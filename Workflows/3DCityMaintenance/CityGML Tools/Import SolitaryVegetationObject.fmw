FME workspace Import SolitaryVegetationObject.fmw

Parameters:
- SourceDataset_CITYGML_3 =   # Source CityGML File(s)
- CITYGML_IN_SRS_AXIS_ORDER_CITYGML =   # GML SRS Axis Order
- CITYGML_IN_SKIP_SCHEMA_LOCATION_IN_DATASET_CITYGML = Yes   # Ignore xsi:schemaLocation in Dataset
- DestDataset_GEODATABASE_FILE =   # Destination Esri File Geodatabase
- GEODATABASE_FILE_OUT_TEMPLATEFILE_GEODATABASE_FILE =   # XML Workspace Document (for initial creation of Geodatabase schema)
- GEODATABASE_FILE_OUT_OVERWRITE_GEODB_GEODATABASE_FILE = No   # Overwrite Existing Geodatabase

Readers:
- CITYGML_1: CITYGML from $(SourceDataset_CITYGML_3)

Writers:
- GEODATABASE_FILE_1: GEODATABASE_FILE to $(DestDataset_GEODATABASE_FILE)

Bookmark: SolitaryVegetationObject - Tree
SolitaryVegetationObject (reader CITYGML_1)
    attributes: citygml_target_uri xml_buffer, citygml_feature_role_attr_name xml_buffer, citygml_feature_role_attr_val xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class_codeSpace xml_buffer, citygml_species_codeSpace xml_buffer, citygml_level_of_detail{} xml_buffer
    -> AttributeValueMapper_2
AttributeValueMapper_2
    DIRECTION = Forward (Source To Destination)
    VAL_ATTR = type
    DEFAULT_VALUE = Other
    LUT = 1000,Picea,1010,Pinus,1020,Other,1030,Other,1040,Fagus,1050,Betula,1060,Alnus,1070,Populus,1080,Salix,1090,Acer,1100,Fraxinus,1110,Other,1120,Other,1130,Other,1140,Other,1150,Other,1160,Other,1170,Other,1180,Other,1190,Other,1200,Other,1210,Other,1220,Other,1230,Other,1240,Other,1250,Other,1260,Other,1270,Other,1280,Other,1290,Other,1300,Other,1310,Other,1320,Other,1330,Other,1340,Other,1350,Other,1360,Other,1370,Other,1380,Other,1390,Other,1400,Other,1410,Other,1420,Other,1430,Other,1440,Other,1450,Magnolia,1460,Other,1470,Other,1480,Other,1490,Other,1500,Rhododendron,1510,Other,1520,Other,1530,Other,1540,Other,1550,Other,1560,Other,1570,Other,1580,Other,1590,Other,1600,Other,1610,Other,1620,Other,1630,Other,1640,Abies,1650,Abies,1660,Abies,1670,Abies,1680,Abies,1690,Abies,1700,Abies,1710,Abies,1720,Abies,1730,Abies,1740,Abies,1750,Abies,1760,Acer,1770,Acer,1780,Acer,1790,Acer,1800,Acer,1810,Acer,1820,Acer,1830,Acer,1840,Acer,1850,Acer,1860,Acer,1870,Acer,1880,Acer,1890,Acer,1900,Acer,1910,Acer,1920,Acer,1930,Aesculus,1940,Aesculus,1950,Other,1960,Ailanthus,1970,Alnus,1980,Alnus,1990,Alnus,2000,Alnus,2010,Other,2020,Other,2030,Aralia,2040,Other,2050,Other,2060,Other,2070,Other,2080,Betula,2090,Betula,2100,Betula,2110,Betula,2120,Betula,2130,Other,2140,Betula,2150,Other,2160,Other,2170,Other,2180,Other,2190,Calocedrus,2200,Other,2210,Other,2220,Other,2230,Other,2240,Carpinus,2250,Other,2260,Castanea,2270,Other,2280,Other,2290,Other,2300,Other,2310,Other,2320,Other,2330,Other,2340,Celtis,2350,Cercis,2360,Other,2370,Chamaecyparis,2380,Chamaecyparis,2390,Other,2400,Other,2410,Other,2420,Other,2430,Other,2440,Cornus,2450,Cornus,2460,Cornus,2470,Cornus,2480,Corylus,2490,Corylus,2500,Corylus,2510,Corylus,2520,Other,2530,Other,2540,Crataegus,2550,Crataegus,2560,Crataegus,2570,Crataegus,2580,Other,2590,Cupressus,2600,Cupressus,2610,Other,2620,Other,2630,Other,2640,Other,2650,Elaeagnus,2660,Elaeagnus,2670,Other,2680,Other,2690,Other,2700,Fagus,2710,Fagus,2720,Fagus,2730,Fagus,2740,Other,2750,Other,2760,Frangula,2770,Fraxinus,2780,Fraxinus,2790,Fraxinus,2800,Fraxinus,2810,Other,2820,Gleditsia,2830,Other,2840,Hamamelis,2850,Hamamelis,2860,Other,2870,Other,2880,Other,2890,Ilex,2900,Other,2910,Juglans,2920,Juglans,2930,Juniperus,2940,Juniperus,2950,Other,2960,Other,2970,Other,2980,Other,2990,Other,3000,Other,3010,Larix,3020,Larix,3030,Ligustrum,3040,Liquidambar,3050,Liquidambar,3060,Liquidambar,3070,Other,3080,Other,3090,Other,3100,Other,3110,Magnolia,3120,Other,3130,Other,3140,Other,3150,Other,3160,Other,3170,Other,3180,Ostrya,3190,Other,3200,Other,3210,Other,3220,Other,3230,Other,3240,Picea,3250,Picea,3260,Picea,3270,Picea,3280,Picea,3290,Picea,3300,Picea,3310,Picea,3320,Picea,3330,Picea,3340,Picea,3350,Pinus,3360,Pinus,3370,Pinus,3380,Pinus,3390,Pinus,3400,Pinus,3410,Pinus,3420,Pinus,3430,Pinus,3440,Pinus,3450,Pinus,3460,Pinus,3470,Pinus,3480,Pinus,3490,Pinus,3500,Pinus,3510,Pinus,3520,Pinus,3530,Pinus,3540,Platanus,3550,Platanus,3560,Other,3570,Populus,3580,Populus,3590,Populus,3600,Populus,3610,Populus,3620,Populus,3630,Prunus,3640,Prunus,3650,Prunus,3660,Prunus,3670,Prunus,3680,Prunus,3690,Prunus,3700,Prunus,3710,Prunus,3720,Prunus,3730,Prunus,3740,Prunus,3750,Pseudotsuga,3760,Other,3770,Other,3780,Other,3790,Other,3800,Other,3810,Quercus,3820,Quercus,3830,Quercus,3840,Quercus,3850,Quercus,3860,Quercus,3870,Quercus,3880,Quercus,3890,Quercus,3900,Quercus,3910,Quercus,3920,Quercus,3930,Quercus,3940,Quercus,3950,Quercus,3960,Rhamnus,3970,Rhamnus,3980,Other,3990,Rhus,4000,Other,4010,Other,4020,Robinia,4030,Other,4040,Other,4050,Salix,4060,Salix,4070,Salix,4080,Salix,4090,Salix,4100,Salix,4110,Salix,4120,Salix,4130,Salix,4140,Salix,4150,Salix,4160,Sambucus,4170,Sambucus,4180,Other,4190,Sequoia,4200,Sequoiadendron,4210,Other,4220,Other,4230,Other,4240,Other,4250,Other,4260,Other,4270,Other,4280,Other,4290,Other,4300,Other,4310,Other,4320,Other,4330,Other,4340,Other,4350,Other,4360,Other,4370,Other,4380,Other,4390,Other,4400,Other,4410,Other,4420,Other,4430,Other,4440,Other,4450,Other,4460,Other,4470,Ulmus,4480,Other,4490,Ulmus,4500,Other,4510,Other,4520,Other,4530,Other,4540,Other,4550,Other,4560,Other,4570,Other,4580,Other,4590,Other,4600,Other,4610,Other,4620,Acer,4630,Other,4640,Other,4650,Other,4660,Other,4670,Other,4680,Other,4690,Other,4700,Other,4710,Other,4720,Other,4730,Other,4740,Other,4750,Other,4760,Other,4770,Other,4780,Other,4790,Other,4800,Other,4810,Other,4820,Other,4830,Other,4840,Other,4850,Other,4860,Other,4870,Other,4880,Other,4890,Other,4900,Other,4910,Other,4920,Other,4930,Other,4940,Other,4950,Other,4960,Other,4970,Other,4980,Other,4990,Other,5000,Other,5010,Other,5020,Other,5030,Other,5040,Other,5050,Other,5060,Other,5070,Other,5080,Other,5090,Other,5100,Other,5110,Other,5120,Other,5130,Other,5140,Other,5150,Other,5160,Other,5170,Other,5180,Other,5190,Other,5200,Other,5210,Other,5220,Other,5230,Other,5240,Other,5250,Other,5260,Other,5270,Other,5280,Other,5290,Other,5300,Other,5310,Other,5320,Other,5330,Other,5340,Other,5350,Other,5360,Other,5370,Other,5380,Other,5390,Other,5400,Other,5410,Other,5420,Other,5430,Other,5440,Other,5450,Other,5460,Other,5470,Other,5480,Other,5490,Other,5500,Other,5510,Other,5520,Other,5530,Other,5540,Other,5550,Other,5560,Other,5570,Other,5580,Other,5590,Other,5600,Other,5610,Other,5620,Other,5630,Other,5640,Other,5650,Other,5660,Other,5670,Other,5680,Other,5690,Other,5700,Other,5710,Other,5720,Other,5730,Other,5740,Other,5750,Other,5760,Other,5770,Other,5780,Other,5790,Other,5800,Other,5810,Other,5820,Other,5830,Other,5840,Other,5850,Other,5860,Other,5870,Other,5880,Other,5890,Other,5900,Ilex,5910,Other,5920,Other,5930,Juglans,5940,Other,5950,Other,5960,Other,5970,Other,5980,Other,5990,Other,6000,Other,6010,Other,6020,Liquidambar,6030,Other,6040,Other,6050,Other,6060,Other,6070,Other,6080,Other,6090,Other,6100,Other,6110,Other,6120,Other,6130,Other,6140,Other,6150,Other,6160,Other,6170,Other,6180,Other,6190,Other,6200,Other,6210,Other,6220,Other,6230,Other,6240,Other,6250,Other,6260,Other,6270,Other,6280,Other,6290,Other,6300,Other,6310,Other,6320,Other,6330,Other,6340,Other,6350,Other,6360,Other,6370,Other,6380,Other,6390,Other,6400,Other,6410,Picea,6420,Pinus,6430,Other,6440,Other,6450,Other,6460,Other,6470,Other,6480,Other,6490,Populus,6500,Prunus,6510,Prunus,6520,Prunus,6530,Prunus,6540,Prunus,6550,Prunus,6560,Prunus,6570,Other,6580,Other,6590,Other,6600,Other,6610,Other,6620,Other,6630,Other,6640,Other,6650,Other,6660,Rhododendron,6670,Rhododendron,6680,Other,6690,Other,6700,Other,6710,Other,6720,Other,6730,Other,6740,Other,6750,Other,6760,Salix,6770,Other,6780,Other,6790,Other,6800,Other,6810,Other,6820,Other,6830,Other,6840,Other,6850,Other,6860,Other,6870,Other,6880,Other,6890,Other,6900,Other,6910,Other,6920,Other,6930,Other,6940,Other,6950,Other,6960,Other,6970,Other,6980,Other,6990,Other,7000,Other,7010,Other,7020,Other,7030,Other,7040,Other,7050,Other,7060,Other,7070,Other,7080,Other,7090,Ulmus,7100,Other,7110,Vaccinium,7120,Other,7130,Other,7140,Other,7150,Other,7160,Other,7170,Other,7180,Other,7190,Other,7200,Other,7210,Other,7220,Other,7230,Other,7240,Other,7250,Other,7260,Other,7270,Other,7280,Other,9999,Unknown
    SRC = citygml_species
    -> AttributeCreator_2
AttributeCreator_2
    ATTR_LIST = FID,@Value(fme_feature_type)/@Value(type)/@Count(@Value(fme_feature_type))/1
    -> AttributeRenamer_2
Note: general attribute mapping
AttributeRenamer_2
    ATTR_LIST = gml_name,name,"",gml_description,description,"",citygml_creationDate,beginLifespan,"",citygml_terminationDate,endLifespan,""
    -> GeometryPropertyExtractor
Note: format beginLifespan, / endLifespan
DateFormatter
    DATE_ATTR = beginLifespan,endLifespan
    FMT = FME Date (%Y%m%d)
    SRCFMT = %Y-%m-%d
    -> AttributeCopier_2
AttributeCopier_2
    ATTR_LIST = subtype,citygml_species
    -> AttributeRenamer_3
    -> AttributeRenamer_4
AttributeRenamer_3
    ATTR_LIST = FID,TreeFID,""
    -> BoundsExtractor_6
BoundsExtractor_6
    ZMIN = _zmin
    XMAX = _xmax
    YMAX = _ymax
    -> CenterPointReplacer_5
CenterPointReplacer_5
    CENTERPOINT -> BoundsExtractor_7
BoundsExtractor_7
    YMIN = _ymin
    XMIN = _xmin
    -> 3DPointReplacer_3
3DPointReplacer_3
    XVALATTR = @Value(_xmin)
    ZVALATTR = @Value(_zmin)
    YVALATTR = @Value(_ymin)
    POINT -> AttributeRenamer
AttributeRenamer
    ATTR_LIST = citygml_height,height,"",citygml_crown_diameter,diameter,"",citygml_trunk_diameter,diameterBreastHeight,""
    -> Tree (writer GEODATABASE_FILE_1)
Tree (writer GEODATABASE_FILE_1)
    attributes: TreeFID char(50), name char(100), description char(250), attribution char(250), type char(50), subtype char(50), beginLifespan date, endLifespan date, datePlanted date, height double, diameter double, diameterBreastHeight double, canopyShape char(30)
AttributeRenamer_4
    ATTR_LIST = FID,referenceFID,""
    -> StringConcatenator
StringConcatenator
    PARM_LINE = SpatialVolumeAnnotation/@Value(type)/@Count(SpatialVolumeAnnotation)/1
    VAL_ATTR = SpatialVolumeAnnotationFID
    -> SpatialVolumeAnnotation (writer GEODATABASE_FILE_1)
SpatialVolumeAnnotation (writer GEODATABASE_FILE_1)
    attributes: SpatialVolumeAnnotationFID char(50), name char(100), description char(250), attribution char(250), referenceFID char(50), value char(250), type char(50), subtype char(50), beginLifespan date, endLifespan date

Bookmark: attribution
  store CityGML filename + feature type + geometry_name
GeometryPropertyExtractor
    TRAIT_ATTR_LIST = citygml_lod_name
    GQUERY:
      for $geom in //geometry
      where $geom/count(parent::geometry) = 0
      return number($geom/@fme_id)
    PREFIX_EXTRACTED_TRAITS = No
    EXTRACTTYPE_PARAM = Traits
    EXTRACTED -> StringConcatenator_2
    UNTOUCHED -> StringConcatenator_2
StringConcatenator_2
    PARM_LINE = @Value(fme_basename)/@Value(fme_feature_type)/@Value(citygml_lod_name)
    VAL_ATTR = attribution
    -> PythonCaller

Bookmark: AttributeContainer handling (all attributes not explicitly mapped)
PythonCaller
    PYTHONSOURCE:
      from fmeobjects import FMEFeature
      from re import match

      # Template Class Interface:
      class FeatureProcessor(object):

          def __init__(s):
              #,"citygml_measured_height"
              s.DoNotMapList =[
                  "^fme_.*",
                  "name","xml_type","attribution","citygml_feature_role","citygml_level_of_detail{0}","_FeatureClass","FID",
                  "description","beginLifespan","endLifespan","type","gml_parent_id",
              "citygml_usage","citygml_roof_type","citygml_storeys_above_ground",
              "citygml_storeys_below_ground","citygml_function"]


          def input(s,f):
              #get FeatureType
              fType = f.getAttribute("fme_feature_type")

              if fType == "CityModel":
                  return
              #get AllAttributes
              allAttr = f.getAllAttributeNames()

              ### Nur Attribute, die nicht auf die DoNotMapListe matchen
              for a in filter(lambda x: not any(match(regex,x) for regex in s.DoNotMapList), allAttr):
                  aValue = f.getAttribute(a)
                  #if aValue is None or aValue == "" or aValue is u"":
                  if not aValue:
                      next
                  #New AttributeContainer Feature
                  nF = FMEFeature()
                  #containerFeature.setFeatureType("AttributeContainer")
                  nF.setAttribute("isAttributeContainer","True")
                  #print a
                  nF.setAttribute("path",a)
                  nF.setAttribute("type",0)
                  nF.setAttribute("value",aValue)
                  nF.setAttribute("referenceFID",f.getAttribute("FID"))
                  nF.setAttribute("referenceType",fType)
                  s.pyoutput(nF)

              s.pyoutput(f)

          def close(s):
              pass
    PYTHONSYMBOL = FeatureProcessor
    NEW_ATTRIBUTES = fme_feature_type isAttributeContainer referenceFID referenceType path value type
    -> Tester_2
Tester_2
    TEST_MODE = Automatic
    TEST_DESCRIPTION = ""
    BOOL_OP = OR
    TEST_CLAUSE = TEST @Value(isAttributeContainer) = True
    FAILED -> AttributeKeeper
    PASSED -> AttributeContainer (writer GEODATABASE_FILE_1)
AttributeContainer (writer GEODATABASE_FILE_1)
    attributes: path char(250), type char(30), value char(250), referenceFID char(50), referenceType char(50)
AttributeKeeper
    KEEP_ATTRS = gml_id,gml_parent_id,citygml_feature_role,description,name,beginLifespan,endLifespan,citygml_class,citygml_function,citygml_usage,citygml_species,citygml_height,citygml_height_units,citygml_trunk_diameter,citygml_crown_diameter,fme_feature_type,type,FID,attribution
    -> DateFormatter
