FME workspace Export Building.fmw

Parameters:
- SourceDataset_GEODATABASE_FILE =   # Source Esri File Geodatabase
- DestDataset_CITYGML_3 =   # Destination CityGML Document
- CITYGML_OUT_VERSION_CITYGML = 1.0   # CityGML Version
- Export_Footprint = No   # Export with Building Footprint (CityGML 2.0 only)
- CityModel_name = 3DCIM CityModel Export   # CityModel Name (gml:name)
- Citymodel_description = 3DCIM CityModel Export   # CityModel description (gml:description)

Readers:
- GEODATABASE_FILE_1: GEODATABASE_FILE from $(SourceDataset_GEODATABASE_FILE)

Writers:
- CITYGML_1: CITYGML to $(DestDataset_CITYGML_3)

Building (reader GEODATABASE_FILE_1)
    attributes: geodb_oid integer, OBJECTID integer, BuildingFID char(50), name char(100), description char(250), attribution char(250), usage char(100), type char(50), subtype char(50), totalHeight double, eaveHeight double, roofForm char(30), levelsAboveGround smallint, levelsBelowGround smallint, status char(30), beginLifespan date, endLifespan date, Shape_Length double, Shape_Area double
    -> AttributeContainerReader [input 1]
BuildingShell (reader GEODATABASE_FILE_1)
    attributes: geodb_oid integer, OID integer, BuildingShellFID char(50), name char(100), description char(250), attribution char(250), buildingFID char(50), generator char(255), protectionLevel smallint
    -> AttributeContainerReader [input 1]
BuildingShellPart (reader GEODATABASE_FILE_1)
    attributes: geodb_oid integer, OID integer, BuildingShellPartFID char(50), name char(100), description char(250), attribution char(250), buildingFID char(255), shellFID char(255), type char(255)
    -> AttributeContainerReader [input 1]
BuildingEntrancePoint (reader GEODATABASE_FILE_1)
    attributes: geodb_oid integer, OBJECTID integer, BuildingEntrancePointFID char(50), name char(100), description char(250), attribution char(250), buildingFID char(50), address char(100), isPrimary smallint, accessType char(30)
    -> AttributeContainerReader [input 1]
SpatialPointAnnotation (reader GEODATABASE_FILE_1)
    attributes: geodb_oid integer, OBJECTID integer, SpatialPointAnnotationFID char(50), name char(100), description char(250), attribution char(250), referenceFID char(50), value char(250), type char(50), subtype char(50), beginLifespan date, endLifespan date
    -> AttributeContainerReader [input 1]
SpatialAreaAnnotation (reader GEODATABASE_FILE_1)
    attributes: geodb_oid integer, OBJECTID integer, SpatialAreaAnnotationFID char(50), name char(100), description char(250), attribution char(250), referenceFID char(50), value char(250), type char(50), subtype char(50), beginLifespan date, endLifespan date, Shape_Length double, Shape_Area double
    -> AttributeContainerReader [input 1]
SpatialVolumeAnnotation (reader GEODATABASE_FILE_1)
    attributes: geodb_oid integer, OID integer, SpatialVolumeAnnotationFID char(50), name char(100), description char(250), attribution char(250), referenceFID char(50), value char(250), type char(50), subtype char(50), beginLifespan date, endLifespan date
    -> AttributeContainerReader [input 1]
SpatialLineAnnotation (reader GEODATABASE_FILE_1)
    attributes: geodb_oid integer, OBJECTID integer, SpatialLineAnnotationFID char(50), name char(100), description char(250), attribution char(250), referenceFID char(50), value char(250), type char(50), subtype char(50), beginLifespan date, endLifespan date, Shape_Length double
    -> AttributeContainerReader [input 1]
BuildingInteriorStructure (reader GEODATABASE_FILE_1)
    attributes: geodb_oid integer, OBJECTID integer, BuildingInteriorStructureFID char(50), name char(100), description char(250), attribution char(250), buildingFID char(50), floorFID char(50), type char(50), subtype char(50), baseElevation double, height double, accessType char(30), beginLifespan date, endLifespan date, Shape_Length double, Shape_Area double
    -> AttributeContainerReader [input 1]
BuildingInstallation (reader GEODATABASE_FILE_1)
    attributes: geodb_oid integer, OBJECTID integer, BuildingInstallationFID char(50), name char(100), description char(250), attribution char(250), position char(30), type char(30), subtype char(50), rotation double, spaceFID char(50), beginLifespan date, endLifespan date
    -> AttributeContainerReader [input 1]
BuildingInteriorSpace (reader GEODATABASE_FILE_1)
    attributes: geodb_oid integer, OBJECTID integer, BuildingInteriorSpaceFID char(50), name char(100), description char(250), attribution char(250), buildingFID char(50), floorFID char(50), shortName char(10), type char(50), subtype char(50), accessType char(30), height double, baseElevation double, floorArea double, capacity integer, spaceForm char(50), spaceFunction char(50), spaceUse char(50), beginLifespan date, endLifespan date, Shape_Length double, Shape_Area double
    -> AttributeContainerReader [input 1]
AttributeContainer (reader GEODATABASE_FILE_1)
    attributes: geodb_oid integer, OBJECTID integer, path char(250), type char(30), value char(250), referenceFID char(50), referenceType char(50)
    -> AttributeContainerReader [input 2]
AttributeContainerReader
    BuildingEntrancePoint -> GeometryRemover
    SpatialPointAnnotation -> AttributeSplitter_3
    SpatialAreaAnnotation -> AttributeSplitter_3
    SpatialVolumeAnnotation -> AttributeSplitter_3
    SpatialLineAnnotation -> AttributeSplitter_3
    BuildingInteriorSpace -> GeometryRemover_4
    BuildingInteriorStructure -> Tester_5
    Building -> FeatureMerger_2 [input 1]
    BuildingInstallation -> GeometryRemover_5
    BuildingShell -> FeatureMerger_2 [input 2]
    BuildingShellPart -> AttributeSplitter_5
FeatureMerger_2
    PROCESS_DUPS = Yes
    MERGE_TYPE = Attributes Only
    LIST_NAME = _BuildingParts
    GEOM_TYPE = Build Polygons
    SUPPLIERS_FIRST = No
    JOIN_KEYS = @Value(gml_id) @Value(buildingFID)
    SUPPLIER_PREFIX_DUMMY = YES
    MERGED -> AttributeValueMapper_2
    NOT_MERGED -> AttributeValueMapper_2
AttributeSplitter_3
    LIST_NAME = attributionParts
    ATTR_NAME = attribution
    DELIMITER = /
    TRIM_OPTION = Both
    DROP_EMPTY_PARTS = No
    -> TestFilter
TestFilter
    TEST_LIST:
      BOOL_OP,OR,COMPOSITE_TEST,<Unused>,TEST_CLAUSE,"TEST @Value(attributionParts{1}) = GenericCityObject",GenericCityObject,BOOL_OP,OR,COMPOSITE_TEST,<Unused>,TEST_CLAUSE,"TEST @Value(attributionParts{1}) = BuildingFurniture
      TEST @Value(attributionParts{1}) = IntBuildingInstallation
      TEST @Value(attributionParts{1}) = BuildingInstallation",Installations,BOOL_OP,COMPOSITE,COMPOSITE_TEST,"""1 AND 2""",TEST_CLAUSE,"TEST @Value(fme_feature_type) = SpatialVolumeAnnotation
      TEST @Value(attributionParts{1}) = ClosureSurface",ClosureSurface,BOOL_OP,AND,COMPOSITE_TEST,<Unused>,TEST_CLAUSE,"TEST @Value(fme_feature_type) = SpatialVolumeAnnotation
      TEST @Value(attributionParts{1}) = Room",Room
    DEFAULT_VALUE = <UNFILTERED>
    GenericCityObject -> AttributeCreator_9
    <UNFILTERED> -> AttributeCreator_7
    Room -> AttributeKeeper_2
    Installations -> AttributeSplitter_7
    ClosureSurface -> AttributeRenamer
AttributeCreator_9
    ATTR_LIST = citygml_lod_name,"FME_CONDITIONAL:DEFAULT_VALUE'@Value(attributionParts{3})'BOOL_OP;OR;COMPOSITE_TEST;<Unused>;TEST attributionParts{2} NOT_ATTRIBUTE_IS_EMPTY <Unused>'@Value(attributionParts{2})'FME_NUM_CONDITIONS2___"
    -> GeometryPropertySetter_5
GeometryPropertySetter_5
    OVERWRITE_CHOICE = Yes
    SRC_ATTRS = citygml_lod_name
    COUNTER_CHOICE = Attributes
    SETTYPE_PARAM = Traits
    SET -> GenericCityObject (writer CITYGML_1)
Note: GenericCityObject
GenericCityObject (writer CITYGML_1)

Bookmark: handle Attributes
AttributeValueMapper_2
    DIRECTION = Forward (Source To Destination)
    VAL_ATTR = citygml_function
    DEFAULT_VALUE = 9999
    LUT = Airport Building,1700,Alpine Cabin,1910,Asylum Seeker Home,2390,Bus Station,2520,Car Park,1620,Child Care,2380,Communication/Media Building,1760,Community Center,2250,Comprehensive School,2080,Concert Hall,2150,Credit Institution,1130,Department Store,1160,Equestrian Hall,1900,Farm House,1070,Fire Station,2410,Gas Station,1340,Glass House,2620,Heat Plant,1780,Holiday house,1100,Homeless Shelter,2370,Indoor Swimming Pool,2590,Medical Service,2300,Outpatients Clinic,2330,Police Station,2400,Post Office,2000,Power Station,1700,Public Administration Building,1960,Pump Station,1680,Research Institute,1380,Retail Store,1170,Seniors Centre,2360,Sports Activities Indoors,2550,Train Station,2480,Transformer Station,1710,Underground Garage,1650,Underground Station,2500,Vocational School,2090,Youth Centre,2350,Barn,1880,Barracks,2420,Boathouse,1590,Casino,1300,Castle,2130,Church,2210,Cinema,1280,Consulate,2030,Convent,2290,Court,2020,Depot,1370,Factory,1320,Garage,1630,Gasworks,1770,Hangar,1540,Hospital,2310,Hotel,1210,Kiosk,1180,Library,2190,Mosque,2270,Museum,2160,Office,1120,Parliament,1980,Pharmacy,1190,Prison,2440,Quarry,1390,Residential,1000,Restaurant,1240,Shipyard,1560,Stall,1890,Synagogue,2230,Theatre,2140,Toilet,1830,University,2100,Watermill,1440,Waterworks,1670,Workshop,1330,Zoo,2610,windmill,1430
    SRC = type
    -> AttributeValueMapper_4
AttributeValueMapper_4
    DIRECTION = Forward (Source To Destination)
    VAL_ATTR = citygml_usage
    DEFAULT_VALUE = 9999
    LUT = Educational,2070,Industrial,1310,Office,1120,Residential,1000
    SRC = usage
    -> AttributeValueMapper_5
AttributeValueMapper_5
    DIRECTION = Forward (Source To Destination)
    VAL_ATTR = citygml_roof_type
    LUT = Arched,1110,Complex,1130,Conical,1080,Domical,1090,Flat,1000,Gable,1030,Hip,1040,Mansard,1060,Mono-pitch,1010,Pyramid,1070,Pyramid,1120,Shed,1100
    SRC = roofForm
    -> Tester
    -> FeatureMerger [input 1]

Bookmark: lod0FootPrint
Tester
    TEST_MODE = Automatic
    TEST_DESCRIPTION = ""
    BOOL_OP = AND
    TEST_CLAUSE:
      TEST $(Export_Footprint) = Yes
      TEST $(CITYGML_OUT_VERSION_CITYGML) = 2.0
    PASSED -> GeometryReplacer
    FAILED -> ListExploder
    PASSED -> ListExploder
GeometryReplacer
    ATTR = _FootPrintGeometry
    KIND_LONG = FME Binary
    -> AttributeCreator
AttributeCreator
    ATTR_LIST = citygml_lod_name,lod0FootPrint
    -> GeometryPropertySetter
GeometryPropertySetter
    OVERWRITE_CHOICE = Yes
    SRC_ATTRS = citygml_lod_name
    COUNTER_CHOICE = Attributes
    SETTYPE_PARAM = Traits
    SET -> Aggregator

Bookmark: lodxSolid and lodxMultiSurface
ListExploder
    INDEX_ATTR = _element_index
    MODE = List Elements and Original Attributes
    LIST_ATTR = _BuildingParts{}
    LIST_FOUND -> GeometryReplacer_2
    NOT_FOUND -> GeometryReplacer_2
GeometryReplacer_2
    ATTR = _BuildingPartGeometry
    KIND_LONG = FME Binary
    -> AttributeRemover_2
AttributeRemover_2
    REMOVE_ATTRS = _FootPrintGeometry,_BuildingPartGeometry
    -> GeometryCoercer
GeometryCoercer
    KIND = fme_brep_solid
    COERCED -> AttributeSplitter_2
AttributeSplitter_2
    LIST_NAME = attributionParts
    ATTR_NAME = attribution
    DELIMITER = /
    TRIM_OPTION = Both
    DROP_EMPTY_PARTS = No
    -> AttributeCreator_3
AttributeCreator_3
    ATTR_LIST = citygml_lod_name,"FME_CONDITIONAL:DEFAULT_VALUE'@Value(attributionParts{3})'BOOL_OP;OR;COMPOSITE_TEST;<Unused>;TEST attributionParts{2} NOT_ATTRIBUTE_IS_EMPTY <Unused>'@Value(attributionParts{2})'FME_NUM_CONDITIONS2___"
    -> GeometryPropertySetter_3
GeometryPropertySetter_3
    OVERWRITE_CHOICE = Yes
    SRC_ATTRS = citygml_lod_name
    COUNTER_CHOICE = Attributes
    SETTYPE_PARAM = Traits
    SET -> Tester_2
Tester_2
    TEST_MODE = Automatic
    TEST_DESCRIPTION = ""
    BOOL_OP = AND
    TEST_CLAUSE:
      TEST $(Export_Footprint) = Yes
      TEST $(CITYGML_OUT_VERSION_CITYGML) = 2.0
    FAILED -> Tester_3
    PASSED -> Tester_4
Tester_4
    TEST_MODE = Automatic
    TEST_DESCRIPTION = ""
    BOOL_OP = OR
    TEST_CLAUSE = TEST @Value(attributionParts{0}) = Building
    PASSED -> AttributeRenamer_3
Tester_3
    TEST_MODE = Automatic
    TEST_DESCRIPTION = ""
    BOOL_OP = OR
    TEST_CLAUSE = TEST @Value(attributionParts{1}) = Building
    FAILED -> AttributeCreator_5
    PASSED -> AttributeRenamer_3
AttributeRenamer_3
    ATTR_LIST = buildingFID,gml_id,""
    -> Aggregator
AttributeCreator_5
    ATTR_LIST = citygml_feature_role,consistsOfBuildingPart
    -> AttributeRenamer_4
AttributeRenamer_4
    ATTR_LIST = buildingFID,gml_parent_id,""
    -> BuildingPart (writer CITYGML_1)

Bookmark: Building and BuildingPart
Note: BuildingPart
BuildingPart (writer CITYGML_1)
Aggregator
    GROUP_BY = gml_id
    MODE = Assemble One Level
    ACCUM_ATTRS_NAME = No
    SEP = ,
    AGGREGATE_TYPE = Homogeneous Collection (If Possible)
    ORDERED = No
    AGGREGATE -> FeatureMerger [input 2]
FeatureMerger
    PROCESS_DUPS = No
    MERGE_TYPE = Geometry
    SUPPLIERS_FIRST = No
    JOIN_KEYS = @Value(gml_id) @Value(gml_id)
    SUPPLIER_PREFIX_DUMMY = YES
    MERGED -> Building (writer CITYGML_1)
    NOT_MERGED -> Building (writer CITYGML_1)
Note: Building
Building (writer CITYGML_1)

Bookmark: lodxTerrainIntersection, lodxMultiCurve
AttributeCreator_7
    ATTR_LIST = citygml_lod_name,"FME_CONDITIONAL:DEFAULT_VALUE'@Value(attributionParts{3})'BOOL_OP;OR;COMPOSITE_TEST;<Unused>;TEST attributionParts{2} NOT_ATTRIBUTE_IS_EMPTY <Unused>'@Value(attributionParts{2})'FME_NUM_CONDITIONS2___"
    -> GeometryPropertySetter_4
GeometryPropertySetter_4
    OVERWRITE_CHOICE = Yes
    SRC_ATTRS = citygml_lod_name
    COUNTER_CHOICE = Attributes
    SETTYPE_PARAM = Traits
    SET -> AttributeKeeper
AttributeKeeper
    KEEP_ATTRS = referenceFID
    -> AttributeRenamer_5
AttributeRenamer_5
    ATTR_LIST = referenceFID,gml_id,""
    -> Aggregator

Bookmark: Room
AttributeKeeper_2
    KEEP_LIST = attributionParts{}
    KEEP_ATTRS = referenceFID
    -> GeometryCoercer_2
GeometryCoercer_2
    KIND = fme_brep_solid
    COERCED -> AttributeCreator_11
AttributeCreator_11
    ATTR_LIST = citygml_lod_name,"FME_CONDITIONAL:DEFAULT_VALUE'@Value(attributionParts{3})'BOOL_OP;OR;COMPOSITE_TEST;<Unused>;TEST attributionParts{2} NOT_ATTRIBUTE_IS_EMPTY <Unused>'@Value(attributionParts{2})'FME_NUM_CONDITIONS2___"
    -> GeometryPropertySetter_8
GeometryPropertySetter_8
    OVERWRITE_CHOICE = Yes
    SRC_ATTRS = citygml_lod_name
    COUNTER_CHOICE = Attributes
    SETTYPE_PARAM = Traits
    SET -> FeatureMerger_3 [input 2]
GeometryRemover_4
    -> AttributeRenamer_6
Note: general Attirbute mapping
AttributeRenamer_6
    ATTR_LIST = buildingFID,gml_parent_id,""
    -> AttributeCreator_12
AttributeCreator_12
    ATTR_LIST = citygml_feature_role,interiorRoom
    -> FeatureMerger_3 [input 1]
FeatureMerger_3
    PROCESS_DUPS = No
    MERGE_TYPE = Attributes and Geometry
    SUPPLIERS_FIRST = No
    JOIN_KEYS = @Value(gml_id) @Value(referenceFID)
    SUPPLIER_PREFIX_DUMMY = YES
    MERGED -> Room (writer CITYGML_1)
    NOT_MERGED -> Room (writer CITYGML_1)
Room (writer CITYGML_1)
AttributeSplitter_6
    LIST_NAME = attributionParts
    ATTR_NAME = attribution
    DELIMITER = /
    TRIM_OPTION = Both
    DROP_EMPTY_PARTS = No
    -> FaceReplacer
FaceReplacer
    CHECK_PLANARITY = No
    -> GeometryCoercer_3
GeometryCoercer_3
    KIND = fme_composite_surface
    COERCED -> AttributeRenamer_7
AttributeRenamer_7
    ATTR_LIST = floorFID,gml_parent_id,""
    -> AttributeCreator_8
AttributeCreator_8
    ATTR_LIST = citygml_lod_name,"FME_CONDITIONAL:DEFAULT_VALUE'@Value(attributionParts{3})'BOOL_OP;OR;COMPOSITE_TEST;<Unused>;TEST attributionParts{2} NOT_ATTRIBUTE_IS_EMPTY <Unused>'@Value(attributionParts{2})'FME_NUM_CONDITIONS2___",_BoundarySurfaceType,@Value(attributionParts{1}),citygml_feature_role,boundedBy
    -> GeometryPropertySetter_6
GeometryPropertySetter_6
    OVERWRITE_CHOICE = Yes
    SRC_ATTRS = citygml_lod_name
    COUNTER_CHOICE = Attributes
    SETTYPE_PARAM = Traits
    SET -> BoundarySurface_ (writer CITYGML_1)
Note: _BoundarySurfaces
BoundarySurface_ (writer CITYGML_1)

Bookmark: BuildingInstallation, IntBuildingInstallation, and BuildingFurniture
AttributeSplitter_7
    LIST_NAME = attributionParts
    ATTR_NAME = attribution
    DELIMITER = /
    TRIM_OPTION = Both
    DROP_EMPTY_PARTS = No
    -> AttributeCreator_13
AttributeCreator_13
    ATTR_LIST = citygml_lod_name,"FME_CONDITIONAL:DEFAULT_VALUE'@Value(attributionParts{3})'BOOL_OP;OR;COMPOSITE_TEST;<Unused>;TEST attributionParts{2} NOT_ATTRIBUTE_IS_EMPTY <Unused>'@Value(attributionParts{2})'FME_NUM_CONDITIONS2___",_InstallationType,@Value(attributionParts{1}),citygml_feature_role,@Value(subtype)
    -> GeometryPropertySetter_9
GeometryPropertySetter_9
    OVERWRITE_CHOICE = Yes
    SRC_ATTRS = citygml_lod_name
    COUNTER_CHOICE = Attributes
    SETTYPE_PARAM = Traits
    SET -> FeatureMerger_4 [input 2]
GeometryRemover_5
    -> AttributeRenamer_9
AttributeRenamer_9
    ATTR_LIST = spaceFID,gml_parent_id,""
    -> FeatureMerger_4 [input 1]
FeatureMerger_4
    PROCESS_DUPS = No
    MERGE_TYPE = Attributes and Geometry
    SUPPLIERS_FIRST = No
    JOIN_KEYS = @Value(gml_id) @Value(referenceFID)
    SUPPLIER_PREFIX_DUMMY = YES
    MERGED -> Tester_6
Tester_6
    TEST_MODE = Automatic
    TEST_DESCRIPTION = ""
    BOOL_OP = OR
    TEST_CLAUSE = TEST @Value(citygml_lod_name) NOT_MATCHES_REGEX lod[1-4]MultiSurface
    PASSED -> BuildingFurniture (writer CITYGML_1)
    FAILED -> AttributeRenamer_10
BuildingFurniture (writer CITYGML_1)
AttributeRenamer_10
    ATTR_LIST = gml_id,gml_parent_id,""
    -> AttributeCreator_14
AttributeCreator_14
    ATTR_LIST = citygml_lod_name,"FME_CONDITIONAL:DEFAULT_VALUE'@Value(attributionParts{3})'BOOL_OP;OR;COMPOSITE_TEST;<Unused>;TEST attributionParts{2} NOT_ATTRIBUTE_IS_EMPTY <Unused>'@Value(attributionParts{2})'FME_NUM_CONDITIONS2___",_BoundarySurfaceType,@Value(attributionParts{1}),citygml_feature_role,boundedBy
    -> GeometryPropertySetter_10
GeometryPropertySetter_10
    OVERWRITE_CHOICE = Yes
    SRC_ATTRS = citygml_lod_name
    COUNTER_CHOICE = Attributes
    SETTYPE_PARAM = Traits
    SET -> BoundarySurface_00 (writer CITYGML_1)
Note: _BoundarySurfaces
BoundarySurface_00 (writer CITYGML_1)

Bookmark: BuildingShellPart to _BoundarySurfaces
AttributeSplitter_5
    LIST_NAME = attributionParts
    ATTR_NAME = attribution
    DELIMITER = /
    TRIM_OPTION = Both
    DROP_EMPTY_PARTS = No
    -> AttributeRenamer
AttributeRenamer
    ATTR_LIST = buildingFID,gml_parent_id,""
    -> AttributeCreator_2
Note: citygml_lod_name / ctiygml_feature_role
AttributeCreator_2
    ATTR_LIST = citygml_lod_name,lod2MultiSurface,citygml_feature_role,boundedBy,_BoundarySurfaceType,"FME_CONDITIONAL:DEFAULT_VALUE'WallSurface'BOOL_OP;OR;COMPOSITE_TEST;<Unused>;TEST @Value(attributionParts{1}) CONTAINS Surface'@Value(attributionParts{1})'FME_NUM_CONDITIONS2___"
    -> GeometryPropertySetter_2
GeometryPropertySetter_2
    OVERWRITE_CHOICE = Yes
    SRC_ATTRS = citygml_lod_name
    COUNTER_CHOICE = Attributes
    SETTYPE_PARAM = Traits
    SET -> BoundarySurface (writer CITYGML_1)
Note: _BoundarySurfaces
BoundarySurface (writer CITYGML_1)

Bookmark: BuildingAddress
GeometryRemover
    -> AttributeRenamer_2
AttributeRenamer_2
    ATTR_LIST = buildingFID,gml_parent_id,""
    -> AttributeSplitter
AttributeSplitter
    LIST_NAME = _addressParts
    ATTR_NAME = address
    DELIMITER = ,
    TRIM_OPTION = Both
    DROP_EMPTY_PARTS = No
    -> XMLTemplater
Note: CityGML makes use of xAL-address schema
XMLTemplater
    RESULT_ATTRIBUTE = citygml_address
    ROOT_QUERY_EXPR:
      <xAL:AddressDetails xmlns:xAL="urn:oasis:names:tc:ciq:xsdschema:xAL:2.0">
          <xAL:Country>
              <xAL:CountryName>{fme:get-list-attribute("_addressParts{3}")}</xAL:CountryName>
              <xAL:Locality Type="Town">
                  <xAL:LocalityName>{fme:get-list-attribute("_addressParts{2}")}</xAL:LocalityName>
                  <xAL:Thoroughfare Type="Street">
                      <xAL:ThoroughfareNumber>{fme:get-list-attribute("_addressParts{1}")}</xAL:ThoroughfareNumber>
                      <xAL:ThoroughfareName>{fme:get-list-attribute("_addressParts{0}")}</xAL:ThoroughfareName>
                  </xAL:Thoroughfare>
              </xAL:Locality>
          </xAL:Country>
      </xAL:AddressDetails>
    VISIBLE_QUERY_VALIDATE = Yes
    OUTPUT_XML_HEADER = Yes
    -> AttributeCreator_4
Note: citygml_lod_name / ctiygml_feature_role
AttributeCreator_4
    ATTR_LIST = citygml_feature_role,@Value(address)
    -> Address (writer CITYGML_1)
Note: Address
Address (writer CITYGML_1)

Bookmark: Opening (Window, Door)
Tester_5
    TEST_MODE = Automatic
    TEST_DESCRIPTION = ""
    BOOL_OP = OR
    TEST_CLAUSE:
      TEST @Value(type) = Window Pane
      TEST @Value(type) = Door
    PASSED -> AttributeSplitter_4
    FAILED -> AttributeSplitter_6
AttributeSplitter_4
    LIST_NAME = attributionParts
    ATTR_NAME = attribution
    DELIMITER = /
    TRIM_OPTION = Both
    DROP_EMPTY_PARTS = No
    -> AttributeRenamer_8
AttributeRenamer_8
    ATTR_LIST = floorFID,gml_parent_id,""
    -> FaceReplacer_2
FaceReplacer_2
    CHECK_PLANARITY = No
    PLANARITY_TOLERANCE = 0.0
    -> AttributeCreator_10
AttributeCreator_10
    ATTR_LIST = citygml_lod_name,"FME_CONDITIONAL:DEFAULT_VALUE'@Value(attributionParts{3})'BOOL_OP;OR;COMPOSITE_TEST;<Unused>;TEST attributionParts{2} NOT_ATTRIBUTE_IS_EMPTY <Unused>'@Value(attributionParts{2})'FME_NUM_CONDITIONS2___",_OpeningType,@Value(attributionParts{1}),citygml_feature_role,opening
    -> GeometryPropertySetter_7
GeometryPropertySetter_7
    OVERWRITE_CHOICE = Yes
    SRC_ATTRS = citygml_lod_name
    COUNTER_CHOICE = Attributes
    SETTYPE_PARAM = Traits
    SET -> Door (writer CITYGML_1)
Door (writer CITYGML_1)

Bookmark: CityModel
Creator
    NUM = 1
    GEOMTYPE = Geometry Object
    CREATED -> AttributeCreator_6
AttributeCreator_6
    ATTR_LIST = gml_name,$(CityModel_name),gml_description,$(Citymodel_description)
    -> CityModel (writer CITYGML_1)
CityModel (writer CITYGML_1)

FME custom transformer AttributeContainerReader

FCL (input)
    -> BulkAttributeRenamer
BulkAttributeRenamer
    REPLACE_STR = gml_id
    ATTRCHOICE = Selected Attributes
    PATTERN_ACTION_DISP = Regular Expression Replace
    ATTRLIST = BuildingFID SpatialPointAnnotationFID SpatialAreaAnnotationFID SpatialVolumeAnnotationFID SpatialLineAnnotationFID BuildingEntrancePointFID BuildingInteriorStructureFID BuildingInteriorSpaceFID BuildingShellPartFID BuildingShellFID BuildingInstallationFID
    REPLACE_PATTERN = .*FID
    -> FeatureMerger [input 1]
AttributeContainer (input)
    -> Aggregator_2
Aggregator_2
    GROUP_BY = referenceFID
    MODE = Assemble One Level
    ACCUM_ATTRS_NAME = No
    LIST_NAME = _AttributeContainer
    SEP = ,
    AGGREGATE_TYPE = Homogeneous Collection (If Possible)
    ORDERED = No
    AGGREGATE -> ListElementCounter
ListElementCounter
    LIST_NAME = _AttributeContainer{}
    CNT_ATTR = _element_count
    -> FeatureMerger [input 2]
FeatureMerger
    PROCESS_DUPS = No
    MERGE_TYPE = Attributes Only
    SUPPLIERS_FIRST = No
    JOIN_KEYS = @Value(gml_id) @Value(referenceFID)
    SUPPLIER_PREFIX_DUMMY = YES
    MERGED -> StringReplacer_3
    NOT_MERGED -> StringReplacer_3
Note: replace "/" with "-" for / all attributes used as gml:id / or gml_parent_id
StringReplacer_3
    SRC_ATTRS = gml_id,referenceFID,buildingFID,floorFID,shellFID,spaceFID
    REGEXP = no
    CASE = no
    REPLACE_TEXT = -
    NO_MATCH = _FME_NO_OP_
    FIND_TEXT = /
    -> PythonCaller
PythonCaller
    PYTHONSOURCE:
      # Template Class Interface:
      class FeatureProcessor(object):
          def __init__(s):
              pass
          def input(s,f):
              count = f.getAttribute("_element_count")
              if count >= 1:
                  for i in range (0,int(count)):
                      path = f.getAttribute("_AttributeContainer{"+str(i)+"}.path")
                      #logger.logMessageString(path)
                      value = f.getAttribute("_AttributeContainer{"+str(i)+"}.value")
                      #logger.logMessageString(path + value)
                      if path != "gml_id":
                          f.setAttribute(path,value)
              s.pyoutput(f)

          def close(self):
              pass
    PYTHONSYMBOL = FeatureProcessor
    NEW_ATTRIBUTES = citygml_year_of_construction citygml_year_of_demolition citygml_class citygml_measured_height_units citygml_storey_heights_above_ground citygml_storey_heights_above_ground_units citygml_storey_heights_below_ground citygml_storey_heights_below_ground_units citygml_usage citygml_function citygml_relativeToTerrain citygml_relativeToWater citygml_lod citygml_isMovable citygml_surfaceMaterial citygml_species citygml_height citygml_trunkDiameter citygml_crownDiameter citygml_averageHeight
    -> AttributeRemover
AttributeRemover
    LIST_ATTRS = _AttributeContainer{}.type _AttributeContainer{}.referenceType _AttributeContainer{}.referenceFID _AttributeContainer{}.value _AttributeContainer{}.geodb_oid _AttributeContainer{}.path _AttributeContainer{} _AttributeContainer{}.OBJECTID _AttributeContainer{}.fme_feature_type
    -> AttributeRenamer_13
Note: general Attirbute mapping
AttributeRenamer_13
    ATTR_LIST = name,gml_name,"",description,gml_description,"",beginLifespan,citygml_creationDate,"",endLifespan,citygml_terminationDate,"",totalHeight,citygml_measured_height,"",levelsAboveGround,citygml_storeys_above_ground,"",levelsBelowGround,citygml_storeys_below_ground,""
    -> TestFilter
TestFilter
    TEST_LIST = BOOL_OP,OR,COMPOSITE_TEST,<Unused>,TEST_CLAUSE,"TEST citygml_creationDate NOT_ATTRIBUTE_IS_EMPTY <Unused>",creationDate,BOOL_OP,OR,COMPOSITE_TEST,<Unused>,TEST_CLAUSE,"TEST citygml_terminationDate NOT_ATTRIBUTE_IS_EMPTY <Unused>",terminationDate
    DEFAULT_VALUE = <UNFILTERED>
    creationDate -> DateFormatter
    terminationDate -> DateFormatter_2
    <UNFILTERED> -> NullAttributeRemover
DateFormatter
    DATE_ATTR = citygml_creationDate
    FMT = XML Date (%Y-%m-%d)
    -> NullAttributeRemover
DateFormatter_2
    DATE_ATTR = citygml_terminationDate
    FMT = XML Date (%Y-%m-%d)
    -> NullAttributeRemover
Note: remove empty attributes / to avoid empy xml tags
NullAttributeRemover
    SRC_ATTRS = geodb_oid,OBJECTID,gml_id,gml_name,gml_description,attribution,usage,type,subtype,citygml_measured_height,eaveHeight,roofForm,citygml_storeys_above_ground,citygml_storeys_below_ground,status,citygml_creationDate,citygml_terminationDate,Shape_Length,Shape_Area,fme_feature_type,referenceFID,value,OID,address,isPrimary,accessType,baseElevation,height,shortName,floorArea,capacity,spaceForm,spaceFunction,spaceUse,generator,protectionLevel,rotation,path,referenceType,_element_count,citygml_year_of_construction,citygml_year_of_demolition,citygml_class,citygml_measured_height_units,citygml_storey_heights_above_ground,citygml_storey_heights_above_ground_units,citygml_storey_heights_below_ground,citygml_storey_heights_below_ground_units,citygml_usage,citygml_function,citygml_relativeToTerrain,citygml_relativeToWater,citygml_lod,citygml_isMovable,citygml_surfaceMaterial,citygml_species,citygml_height,citygml_trunkDiameter,citygml_crownDiameter,citygml_averageHeight
    -> FeatureTypeFilter
FeatureTypeFilter
    ATTRIBUTES = <BLANK>,<UNFILTERED>,Building,BuildingShell,BuildingShellPart,BuildingEntrancePoint,BuildingInteriorSpace,BuildingInteriorStructure,BuildingInstallation,SpatialPointAnnotation,SpatialAreaAnnotation,SpatialVolumeAnnotation,SpatialLineAnnotation
    BuildingShellPart -> BuildingShellPart (output)
    BuildingEntrancePoint -> BuildingEntrancePoint (output)
    BuildingInteriorSpace -> BuildingInteriorSpace (output)
    BuildingInteriorStructure -> BuildingInteriorStructure (output)
    SpatialPointAnnotation -> SpatialPointAnnotation (output)
    SpatialAreaAnnotation -> SpatialAreaAnnotation (output)
    SpatialVolumeAnnotation -> SpatialVolumeAnnotation (output)
    SpatialLineAnnotation -> SpatialLineAnnotation (output)
    Building -> GeometryExtractor
    BuildingShell -> GeometryExtractor_2
    BuildingInstallation -> BuildingInstallation (output)
GeometryExtractor
    ATTR = _FootPrintGeometry
    KIND_LONG = FME Binary
    -> GeometryRemover_2
GeometryRemover_2
    -> Building (output)
Building (output)
GeometryExtractor_2
    ATTR = _BuildingPartGeometry
    KIND_LONG = FME Binary
    -> GeometryRemover_3
GeometryRemover_3
    -> BuildingShell (output)
BuildingShell (output)
BuildingShellPart (output)
BuildingEntrancePoint (output)
BuildingInteriorSpace (output)
BuildingInteriorStructure (output)
BuildingInstallation (output)
SpatialPointAnnotation (output)
SpatialAreaAnnotation (output)
SpatialVolumeAnnotation (output)
SpatialLineAnnotation (output)

FME custom transformer NullAttributeRemover
Checks all the selected attributes and removes them if their contents are 0 or blank. 
This transformer is useful when you need a NULL value written to a database format instead of blank or 0.
The transformer takes one parameter:
Attributes: The attributes to test.
Copyright (c) 2012 Safe Software Inc.
Permission is granted to anyone, free of charge, to use, modify and distribute the object code form of this template for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTRS =   # " " Attributes

INPUT (input)
    -> ParameterFetcher
ParameterFetcher
    ATTR_LIST = _SRC_ATTRS {$(SRC_ATTRS)}
    -> PythonCaller
PythonCaller
    PYTHONSOURCE:
      import fmeobjects
      # Template Function interface:
      def removeNulls(feature):
         attrsin = feature.getAttribute('_SRC_ATTRS')
         attrs = attrsin.split(',')
         for attr in attrs:
             val = feature.getAttribute(attr)
             if not val:
                 feature.removeAttribute(attr)
    PYTHONSYMBOL = removeNulls
    -> AttributeRemover
AttributeRemover
    REMOVE_ATTRS = _SRC_ATTRS
    -> OUTPUT (output)
OUTPUT (output)
