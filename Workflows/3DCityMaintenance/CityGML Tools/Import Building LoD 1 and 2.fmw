FME workspace Import Building LoD 1 and 2.fmw

Parameters:
- SourceDataset_CITYGML =   # Source CityGML File(s)
- CITYGML_IN_SRS_AXIS_ORDER_CITYGML =   # GML SRS Axis Order (optional)
- CITYGML_IN_SKIP_SCHEMA_LOCATION_IN_DATASET_CITYGML = Yes   # Ignore xsi:schemaLocation in Dataset (optional)
- DestDataset_GEODATABASE_FILE =   # Destination Esri File Geodatabase
- GEODATABASE_FILE_OUT_TEMPLATEFILE_GEODATABASE_FILE =   # Template File
- GEODATABASE_FILE_OUT_OVERWRITE_GEODB_GEODATABASE_FILE = Yes   # Overwrite Existing Geodatabase

Readers:
- CITYGML_1: CITYGML from $(SourceDataset_CITYGML)

Writers:
- GEODATABASE_FILE_1: GEODATABASE_FILE to $(DestDataset_GEODATABASE_FILE)

IntBuildingInstallation (reader CITYGML_1)
    attributes: citygml_target_uri xml_buffer, citygml_feature_role_attr_name xml_buffer, citygml_feature_role_attr_val xml_buffer, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_consists_of_building_part{}.xlink_href xml_buffer, citygml_relief_component{}.xlink_href xml_buffer, citygml_interior_room{}.xlink_href xml_buffer, citygml_parent_xlink_href xml_buffer, citygml_opening{}.xlink_href xml_buffer, citygml_city_object_member{}.xlink_href xml_buffer, citygml_outer_building_installation{}.xlink_href xml_buffer, citygml_auxiliary_traffic_area{}.xlink_href xml_buffer, citygml_group_member{}.role xml_buffer, gml_feature_member{}.xlink_href xml_buffer, citygml_interior_furniture{}.xlink_href xml_buffer, citygml_address{}.xlink_href xml_buffer, citygml_appearance_member{}.xlink_href xml_buffer, citygml_traffic_area{}.xlink_href xml_buffer, citygml_interior_building_installation{}.xlink_href xml_buffer, citygml_group_member{}.xlink_href xml_buffer, citygml_room_installation{}.xlink_href xml_buffer, citygml_bounded_by{}.xlink_href xml_buffer
    -> CityGMLAttributeMapper
CityGMLAttributeMapper: CityGMLMapper
    AttributeContainer -> AttributeContainer (writer GEODATABASE_FILE_1)
    Building -> FeatureMerger [input 2]
    BuildingPart -> FeatureMerger [input 1]
    BuildingShellPart -> FeatureMerger_5 [input 1]
Note: AttributeContainer / (store all attributes not / explicitly mapped)
AttributeContainer (writer GEODATABASE_FILE_1)
    attributes: path char(250), type char(30), value char(250), referenceFID char(50), referenceType char(50)

Bookmark: Building, BuildingShell, and BuildingShellPart
Note: if Multiple Representations / (flatten one level)
FeatureMerger
    PROCESS_DUPS = No
    MERGE_TYPE = Attributes Only
    SUPPLIERS_FIRST = No
    JOIN_KEYS = @Value(gml_parent_id) @Value(gml_id)
    SUPPLIER_PREFIX_DUMMY = YES
    MERGED -> FeatureMerger_5 [input 2]
    NOT_MERGED -> FeatureMerger_5 [input 2]
    UNREFERENCED -> FeatureMerger_5 [input 2]
FeatureMerger_5
    PROCESS_DUPS = No
    MERGE_TYPE = Attributes Only
    SUPPLIERS_FIRST = No
    JOIN_KEYS = @Value(BoundarySurface_gml_parent_id) @Value(gml_id)
    SUPPLIER_PREFIX_DUMMY = YES
    MERGED -> Tester_8
    UNREFERENCED -> TestFilter_3
Tester_8
    TEST_MODE = Automatic
    TEST_DESCRIPTION = ""
    BOOL_OP = AND
    TEST_CLAUSE = TEST @Value(BoundarySurface_type) = Ground Plate
    PASSED -> FootPrintReplacer_3
    PASSED -> AttributeRenamer
    FAILED -> AttributeRenamer
FootPrintReplacer_3
    Aggregator_4_AGGREGATE_69 -> AttributeKeeper
AttributeRenamer
    ATTR_LIST = BuildingFID,buildingFID,""
    -> BulkAttributeRenamer_7
BulkAttributeRenamer_7
    REPLACE_STR = BoundarySurface_
    ATTRCHOICE = All Attributes
    PATTERN_ACTION_DISP = Remove Prefix String
    CASE_DISP = yes
    -> Deaggregator
    -> Aggregator
Deaggregator
    CHILD_ID_ATTR = _hierarchy_child_id_list
    LIST_ATTR_MODE_LOOKUP = LEAN
    MODE = Flatten One Level
    PARENT_ID_ATTR = _hierarchy_parent_id
    ID_SELECTION = ID and Parent ID
    SPLIT_COMPOSITES = No
    PART_NUMBER_FIELD = _part_number
    ID_ATTR = _hierarchy_id
    COPY_ATTR = Every Node
    EXPLODE_INSTANCES = No
    GEOM_NAME_FIELD = _geometry_name
    DEAGGREGATED -> BuildingShellPart (writer GEODATABASE_FILE_1)
TestFilter_3
    TEST_LIST = BOOL_OP,OR,COMPOSITE_TEST,<Unused>,TEST_CLAUSE,"TEST @Value(citygml_lod_name) MATCHES_REGEX lod[1-4]MultiSurface",lod[1-4]MultiSurface,BOOL_OP,OR,COMPOSITE_TEST,<Unused>,TEST_CLAUSE,"TEST @Value(citygml_lod_name) MATCHES_REGEX lod[1-4]Solid",lod[1-4]Solid
    DEFAULT_VALUE = <UNFILTERED>
    lod[1-4]Solid -> Tester_10
    lod[1-4]MultiSurface -> Tester_10
    lod[1-4]MultiSurface -> StringConcatenator_6
    lod[1-4]Solid -> StringConcatenator_6
Tester_10
    TEST_MODE = Automatic
    TEST_DESCRIPTION = ""
    BOOL_OP = OR
    TEST_CLAUSE = TEST @Value(citygml_lod_name) != lod0FootPrint
    PASSED -> GroundSurfaceExtractor_3
GroundSurfaceExtractor_3
    Sampler_SAMPLED_183 -> AttributeKeeper
AttributeKeeper
    KEEP_ATTRS = citygml_storey_heights_above_ground,citygml_year_of_demolition,gml_id,gml_parent_id,citygml_feature_role,description,name,beginLifespan,endLifespan,subtype,citygml_function,citygml_usage,citygml_roof_type,citygml_height,citygml_address,citygml_height_units,totalHeight,citygml_storey_heights_below_ground,citygml_year_of_construction,levelsAboveGround,levelsBelowGround,type,BuildingShellFID,citygml_lod_name,attribution,usage,roofForm,BuildingFID
    -> Building (writer GEODATABASE_FILE_1)

Bookmark: BuildingShell
Aggregator
    GROUP_BY = gml_parent_id
    MODE = Assemble One Level
    ACCUM_ATTRS_NAME = Yes
    SEP = ,
    AGGREGATE_TYPE = Homogeneous Collection (If Possible)
    ORDERED = No
    AGGREGATE -> StringConcatenator_6
StringConcatenator_6
    PARM_LINE = BuildingShell/@Count(BuildingShell)/1
    VAL_ATTR = BuildingShellFID
    -> BuildingShell (writer GEODATABASE_FILE_1)
Note: BuildingShell
BuildingShell (writer GEODATABASE_FILE_1)
    attributes: BuildingShellFID char(50), name char(100), description char(250), attribution char(250), buildingFID char(50), generator char(255), protectionLevel smallint

Bookmark: BuildingShellPart
Note: BuildingShellPart
BuildingShellPart (writer GEODATABASE_FILE_1)
    attributes: BuildingShellPartFID char(50), name char(100), description char(250), attribution char(250), buildingFID char(255), shellFID char(255), type char(255)

Bookmark: Building
Building (writer GEODATABASE_FILE_1)
    attributes: BuildingFID char(50), name char(100), description char(250), attribution char(250), usage char(100), type char(50), subtype char(50), totalHeight double, eaveHeight double, roofForm char(30), levelsAboveGround smallint, levelsBelowGround smallint, status char(30), beginLifespan date, endLifespan date

FME custom transformer FootPrintReplacer

Parameters:
- FME_PROCESS_GROUP_BY =   # " " Parallel Process By

Aggregator_6_INPUT_66 (input)
    -> Aggregator_6
Aggregator_6
    GROUP_BY = $(FME_PROCESS_GROUP_BY)
    MODE = Assemble One Level
    ACCUM_ATTRS_NAME = Yes
    SEP = ,
    AGGREGATE_TYPE = Homogeneous Collection (If Possible)
    ORDERED = No
    AGGREGATE -> BoundsExtractor_2
BoundsExtractor_2
    YMIN = _ymin
    ZMIN = _zmin
    XMIN = _xmin
    XMAX = _xmax
    ZMAX = _zmax
    YMAX = _ymax
    -> Deaggregator_6
Deaggregator_6
    LIST_ATTR_MODE_LOOKUP = LEAN
    MODE = Flatten All Levels
    SPLIT_COMPOSITES = No
    EXPLODE_INSTANCES = No
    GEOM_NAME_FIELD = _geometry_name
    DEAGGREGATED -> GeometryCoercer_6
GeometryCoercer_6
    CHECKZ = No
    KIND = fme_polygon
    COERCED -> 3DForcer
3DForcer
    ZVALATTR = @Value(_zmin)
    -> Dissolver_2
Dissolver_2
    GROUP_BY = $(FME_PROCESS_GROUP_BY)
    NO_OVRLP = No
    ACCUM_INPUT_ATTRS = Yes
    AREA -> Aggregator_4
    <REJECTED> -> Aggregator_4
Aggregator_4
    GROUP_BY = $(FME_PROCESS_GROUP_BY)
    MODE = Assemble One Level
    ACCUM_ATTRS_NAME = Yes
    SEP = ,
    AGGREGATE_TYPE = Homogeneous Collection (If Possible)
    ORDERED = No
    AGGREGATE -> Aggregator_4_AGGREGATE_69 (output)
Aggregator_4_AGGREGATE_69 (output)

FME custom transformer CityGMLMapper

CityModel (input)
    -> TestFilter
Note: exclude X3DMaterial, / Appearance Objects, / ParameterizedTexture, and CityModel
TestFilter
    TEST_LIST:
      BOOL_OP,OR,COMPOSITE_TEST,<Unused>,TEST_CLAUSE,"TEST @Value(fme_feature_type) = Appearance
      TEST @Value(fme_feature_type) = X3DMaterial
      TEST @Value(fme_feature_type) = CityModel
      TEST @Value(fme_feature_type) = ParameterizedTexture",NotUsed
    DEFAULT_VALUE = <UNFILTERED>
    <UNFILTERED> -> TestFilter_2
TestFilter_2
    TEST_LIST:
      BOOL_OP,OR,COMPOSITE_TEST,<Unused>,TEST_CLAUSE,"TEST @Value(fme_feature_type) = Building
      TEST @Value(fme_feature_type) = BuildingPart",BuildingAndBuildingPart,BOOL_OP,OR,COMPOSITE_TEST,<Unused>,TEST_CLAUSE,"TEST @Value(fme_feature_type) = GroundSurface
      TEST @Value(fme_feature_type) = WallSurface
      TEST @Value(fme_feature_type) = RoofSurface
      TEST @Value(fme_feature_type) = OuterCeilingSurface
      TEST @Value(fme_feature_type) = OuterFloorSurface",BuildingShell,BOOL_OP,OR,COMPOSITE_TEST,<Unused>,TEST_CLAUSE,"TEST @Value(fme_feature_type) = Room",Room,BOOL_OP,OR,COMPOSITE_TEST,<Unused>,TEST_CLAUSE,"TEST @Value(fme_feature_type) = InteriorWallSurface
      TEST @Value(fme_feature_type) = CeilingSurface
      TEST @Value(fme_feature_type) = FloorSurface
      TEST @Value(fme_feature_type) = Window
      TEST @Value(fme_feature_type) = Door",BuildingInteriorStructure,BOOL_OP,OR,COMPOSITE_TEST,<Unused>,TEST_CLAUSE,"TEST @Value(fme_feature_type) = BuildingFurniture
      TEST @Value(fme_feature_type) = BuildingInstallation
      TEST @Value(fme_feature_type) = IntBuildingInstallation",BuildingInstallation
    DEFAULT_VALUE = <UNFILTERED>
    BuildingShell -> AttributeValueMapper_3
    <UNFILTERED> -> AttributeCreator
    BuildingAndBuildingPart -> AttributeValueMapper
    Room -> AttributeValueMapper_2
    BuildingInteriorStructure -> AttributeValueMapper_6
    BuildingInstallation -> AttributeCreator_3
Note: create FIDs for / every feature
StringConcatenator
    PARM_LINE = @Value(fme_feature_type)/@Value(type)/@Count(@Value(fme_feature_type))/1
    VAL_ATTR = FID
    -> AttributeRenamer_2
Note: general attribute mapping
AttributeRenamer_2
    ATTR_LIST = gml_name,name,"",gml_description,description,"",citygml_creationDate,beginLifespan,"",citygml_terminationDate,endLifespan,""
    -> DateFormatter
Note: format beginLifespan,endLifespan
DateFormatter
    DATE_ATTR = beginLifespan,endLifespan
    FMT = FME Date (%Y%m%d)
    SRCFMT = %Y-%m-%d
    -> GeometryPropertyExtractor
GenericCityObject (output)

Bookmark: set type attribute
AttributeValueMapper
    DIRECTION = Forward (Source To Destination)
    VAL_ATTR = type
    DEFAULT_VALUE = Other
    LUT = 1000,Residential,1010,Other,1020,Hotel,1030,Residential,1040,Residential,1050,Residential,1060,Residential,1070,Farm House,1080,Residential,1090,Other,1100,Holiday house,1110,Residential,1120,Office,1130,Credit Institution,1140,Office,1150,Office,1160,Department Store,1170,Retail Store,1180,Kiosk,1190,Pharmacy,1200,Other,1210,Hotel,1220,Hotel,1230,Other,1240,Restaurant,1250,Restaurant,1260,Other,1270,Other,1280,Cinema,1290,Sports Activities Indoors,1300,Casino,1310,Heavy Industry Plant,1320,Factory,1330,Workshop,1340,Gas Station,1350,Other,1360,Depot,1370,Depot,1380,Research Institute,1390,Quarry,1400,Factory,1410,Factory,1420,Factory,1430,Workshop,1440,Watermill,1450,Other,1460,Other,1470,Office,1480,Other,1490,Other,1500,Other,1510,Other,1520,Other,1530,Airport Building,1540,Hangar,1550,Harbour Building,1560,Shipyard,1570,Other,1580,Harbour Building,1590,Boathouse,1600,Other,1610,Car Park,1620,Car Park,1630,Garage,1640,Garage,1650,Underground Garage,1660,Other,1670,Waterworks,1680,Pump Station,1690,Other,1700,Power Station,1710,Transformer Station,1720,Transformer Station,1730,Other,1740,Other,1750,Heat Plant,1760,Communication/Media Building,1770,Gasworks,1780,Heat Plant,1790,Pump Station,1800,Other,1810,Other,1820,Other,1830,Toilet,1840,Other,1850,Other,1860,Other,1870,Farm House,1880,Barn,1890,Stall,1900,Equestrian Hall,1910,Alpine Cabin,1920,Other,1930,Museum,1940,Glass House,1950,Glass House,1960,Public Administration Building,1970,Public Administration Building,1980,Parliament,1990,Other,2000,Post Office,2010,Other,2020,Court,2030,Consulate,2040,Public Administration Building,2050,Public Administration Building,2060,Office,2070,University,2080,Comprehensive School,2090,Vocational School,2100,University,2110,University,2120,Other,2130,Castle,2140,Theatre,2150,Concert Hall,2160,Museum,2170,Communication/Media Building,2180,Sports Activities Indoors,2190,Library,2200,Castle,2210,Church,2220,Church,2230,Synagogue,2240,Church,2250,Community Center,2260,Church,2270,Mosque,2280,Church,2290,Convent,2300,Medical Service,2310,Hospital,2320,Medical Service,2330,Outpatients Clinic,2340,Other,2350,Youth Centre,2360,Seniors Centre,2370,Homeless Shelter,2380,Child Care,2390,Asylum Seeker Home,2400,Police Station,2410,Fire Station,2420,Barracks,2430,Other,2440,Prison,2450,Other,2460,Other,2470,Other,2480,Train Station,2490,Airport Building,2500,Underground Station,2510,Other,2520,Bus Station,2530,Harbour Building,2540,Other,2550,Sports Activities Indoors,2560,Sports Activities Indoors,2570,Other,2580,Sports Activities Indoors,2590,Indoor Swimming Pool,2600,Hospital,2610,Zoo,2620,Glass House,2630,Museum,2640,Other,2650,Other,2700,Other
    SRC = citygml_function
    -> StringConcatenator
AttributeValueMapper_3
    DIRECTION = Forward (Source To Destination)
    VAL_ATTR = type
    DEFAULT_VALUE = Other
    LUT = GroundSurface,Ground Plate,WallSurface,Wall,RoofSurface,Roof,OuterCeilingSurface,Other,OuterFloorSurface,Other
    SRC = fme_feature_type
    -> StringConcatenator
AttributeValueMapper_2
    DIRECTION = Forward (Source To Destination)
    VAL_ATTR = type
    DEFAULT_VALUE = Other
    LUT = 1000,Other,1010,Bedroom,1020,Kitchen,1030,Hallway,1040,Other,1050,Restroom,1060,Stairway,1070,Office,1080,Facility Equipment Service Spaces,1090,Dining Room,1100,Other,1110,Other,1120,Nursery,1130,General Retail Space,1140,Kitchen,1150,General Retail Space,1160,Balcony,1170,Other,1180,Laundry Room,1190,Other,1200,Other,1210,Other,1220,Other,1300,Office,1310,Office,1320,Conference Room,1330,Reception Space,1340,Buying and Selling Spaces,1350,General Retail Space,1360,Other,1370,Other,1380,Stairway,1390,Restroom,1400,Other,1500,Office,1510,Entry Lobby,1520,Elevator Cab,1530,Kitchen,1540,Kitchen,1550,Other,1560,Office,1570,Conference Room,1580,Copy Room,1590,Other,1600,Computer Lab,1610,Printing Room,1700,Reception Space,1710,Other,1720,Liquor Bar,1730,Other,1740,Dining Room,1750,Other,1760,Liquor Bar,1770,Other,1780,Other,1790,Storage Room,1800,Bowling Lane,1810,Other,1820,Kitchen,1900,Acting Stage,1910,Auditorium,1920,Other,1930,Audio-Visual Room,1940,Dressing Room,1950,Other,1960,Buying and Selling Spaces,1970,Equipment Room,1980,Other,1990,Other,2000,Other,2010,Other,2020,Other,2030,Office,2040,Library,2050,Audio-Visual Room,2060,Dressing Room,2070,Exercise Space,2080,Equipment Room,2090,Other,2100,Recreation Spaces,2110,Other,2120,Recreation Spaces,2130,Sauna,2140,Exercise Space,2150,Other,2160,Other,2170,Shower,2200,Other,2210,Other,2220,Buying and Selling Spaces,2230,Other,2240,Other,2250,Other,2260,Other,2270,Other,2280,Other,2290,Other,2300,Other,2310,Storage Room,2320,Other,2330,Other,2340,Other,2350,Exercise Space,2360,Other,2370,Other,2400,Other,2410,Other,2420,Other,2430,Other,2440,Control Room,2450,Other,2460,Other,2470,Other,2480,Other,2490,Other,2500,Other,2600,Other,2610,Chapel,2620,Other,2630,Other,2640,Other,2650,Other,2660,Other,2670,Hallway,2680,Other,2690,Chapel,2700,Other,2710,Other,2720,Other,2730,Other,2740,Other,2750,Recreation Spaces,2760,General Retail Space,2770,Other,2780,Other,2790,Other,2800,Other,2810,Other,2900,Other,2910,Other,3000,Other,3010,Other,3020,Other,3030,Other,3040,Warehouse Space,3050,Freezing Compartment,3060,General Retail Space,3100,Other,3110,Other,3120,Office,3130,Hallway,3140,Other,3150,Other,3160,Other,3170,Checkout Space,3180,Checkout Space,3190,Reception Space,3200,Baggage Claim,3210,Other,3300,Classroom,3310,Work Spaces,3320,Break Room,3330,Laboratory,3340,Facility Equipment Service Spaces,3350,Audio-Visual Room,3360,Laboratory,3370,Exercise Space,3380,Library,3390,Office,3400,Other,3410,Other,3420,Other
    SRC = citygml_class
    -> StringConcatenator
AttributeValueMapper_6
    DIRECTION = Forward (Source To Destination)
    VAL_ATTR = type
    DEFAULT_VALUE = Other
    LUT = InteriorWallSurface,Interior Wall,FloorSurface,Other,CeilingSurface,Other,Window,Window Pane,Door,Door
    SRC = fme_feature_type
    -> StringConcatenator
AttributeCreator_3
    ATTR_LIST = type,Structural
    -> StringConcatenator
AttributeCreator
    ATTR_LIST = type,Unknown
    -> StringConcatenator

Bookmark: attribution-attribute
  store CityGML filename + feature type + geometry_name
GeometryPropertyExtractor
    GQUERY:
      for $geom in //geometry
      where $geom/count(parent::geometry) = 0
      return number($geom/@fme_id)
    EXTRACTTYPE_PARAM = Geometry Name
    GEOM_NAME_FIELD = citygml_lod_name
    EXTRACTED -> StringConcatenator_2
    UNTOUCHED -> StringConcatenator_2
StringConcatenator_2
    PARM_LINE = @Value(fme_basename)/@Value(fme_feature_type)/@Value(citygml_lod_name)
    VAL_ATTR = attribution
    -> PythonCaller

Bookmark: AttributeContainer handling (all attributes not explicitly mapped)
PythonCaller
    PYTHONSOURCE:
      from fmeobjects import FMEFeature
      from re import match

      # Template Class Interface:
      class FeatureProcessor(object):

          def __init__(s):
              # preserve attribute explicitly mapped to be stored in
              # AttributeContainer
              s.DoNotMapList =[
                  "^fme_.*",
                  "name","xml_type","attribution","citygml_feature_role","citygml_level_of_detail{0}","FID",
                  "description","beginLifespan","endLifespan","type","gml_parent_id",
                  "citygml_roof_type","citygml_storeys_above_ground",
                  "citygml_storeys_below_ground","multi_reader_full_id","multi_reader_id",
                  "multi_reader_type","multi_reader_keyword",
                  "citygml_target_uri","citygml_lod_name"]

          def input(s,f):
              #get Feature Type
              fType = f.getAttribute("fme_feature_type")

              #get AllAttributes from current feature
              allAttr = f.getAllAttributeNames()

              for a in filter(lambda x: not any(match(regex,x) for regex in s.DoNotMapList), allAttr):
                  aValue = f.getAttribute(a)
                  #if aValue is None or aValue == "" or aValue is u"":
                  if not aValue:
                      next
                  #New AttributeContainer Feature
                  nF = FMEFeature()
                  nF.setAttribute("isAttributeContainer","True")
                  nF.setAttribute("path",a)
                  nF.setAttribute("type",0)
                  nF.setAttribute("value",aValue)
                  nF.setAttribute("referenceFID",f.getAttribute("FID"))
                  nF.setAttribute("referenceType",fType)
                  s.pyoutput(nF)

              s.pyoutput(f)

          def close(s):
              pass
    PYTHONSYMBOL = FeatureProcessor
    NEW_ATTRIBUTES = fme_feature_type isAttributeContainer referenceFID referenceType path value type
    -> Tester_2
Tester_2
    TEST_MODE = Automatic
    TEST_DESCRIPTION = ""
    BOOL_OP = OR
    TEST_CLAUSE = TEST @Value(isAttributeContainer) = True
    PASSED -> AttributeContainer (output)
    FAILED -> AttributeKeeper
AttributeContainer (output)
AttributeKeeper
    KEEP_LIST = citygml_address{}
    KEEP_ATTRS = gml_id,gml_parent_id,citygml_feature_role,description,name,beginLifespan,endLifespan,citygml_address,citygml_height_units,citygml_measured_height,citygml_usage,citygml_function,citygml_year_of_demolition,citygml_roof_type,citygml_height,citygml_storey_heights_below_ground,citygml_year_of_construction,citygml_storeys_above_ground,citygml_storeys_below_ground,citygml_storey_heights_above_ground,citygml_class,fme_feature_type,fme_geometry,fme_type,type,FID,citygml_lod_name,attribution,citygml_address{0}.xlink_href
    -> FeatureTypeFilter

Bookmark: individual attribute mapping
FeatureTypeFilter
    ATTRIBUTES = <BLANK>,<UNFILTERED>,Building,BuildingPart,GroundSurface,WallSurface,RoofSurface,OuterCeilingSurface,OuterFloorSurface,Room,InteriorWallSurface,CeilingSurface,FloorSurface,Window,Door,Address,BuildingFurniture,BuildingInstallation,IntBuildingInstallation,ClosureSurface,GenericCityObject
    ClosureSurface -> ClosureSurface (output)
    Building -> AttributeRenamer_3
    BuildingPart -> AttributeRenamer_3
    Address -> AttributeKeeper_2
    GroundSurface -> AttributeKeeper_3
    WallSurface -> AttributeKeeper_3
    RoofSurface -> AttributeKeeper_3
    OuterCeilingSurface -> AttributeKeeper_3
    OuterFloorSurface -> AttributeKeeper_3
    Room -> AttributeKeeper_4
    InteriorWallSurface -> AttributeKeeper_5
    CeilingSurface -> AttributeKeeper_5
    FloorSurface -> AttributeKeeper_5
    Window -> AttributeKeeper_6
    Door -> AttributeKeeper_6
    GenericCityObject -> GenericCityObject (output)
    BuildingFurniture -> AttributeCreator_2
    BuildingInstallation -> AttributeCreator_2
    IntBuildingInstallation -> AttributeCreator_2
AttributeRenamer_3
    ATTR_LIST = citygml_measured_height,totalHeight,"",citygml_storeys_above_ground,levelsAboveGround,"",citygml_storeys_below_ground,levelsBelowGround,"",FID,BuildingFID,"",citygml_class,subtype,""
    -> AttributeValueMapper_4
Note: usage
AttributeValueMapper_4
    DIRECTION = Forward (Source To Destination)
    VAL_ATTR = usage
    DEFAULT_VALUE = Other
    LUT = 1000,Residential,1010,Residential,1020,Service,1030,Residential,1040,Residential,1050,Residential,1060,Residential,1070,Agricultural,1080,Residential,1090,Agricultural,1100,Residential,1110,Residential,1120,Office,1130,Office,1140,Office,1150,Office,1160,Mercantile,1170,Mercantile,1180,Mercantile,1190,Mercantile,1200,Public,1210,Service,1220,Service,1230,Service,1240,Service,1250,Service,1260,Public,1270,Other,1280,Service,1290,Service,1300,Service,1310,Industrial,1320,Industrial,1330,Service,1340,Service,1350,Service,1360,Service,1370,Service,1380,Educational,1390,Industrial,1400,Industrial,1410,Industrial,1420,Industrial,1430,Industrial,1440,Industrial,1450,Industrial,1460,Other,1470,Transport,1480,Public,1490,Public,1500,Transport,1510,Transport,1520,Transport,1530,Transport,1540,Transport,1550,Transport,1560,Transport,1570,Transport,1580,Transport,1590,Transport,1600,Transport,1610,Transport,1620,Transport,1630,Transport,1640,Transport,1650,Transport,1660,Storage,1670,Utility,1680,Utility,1690,Utility,1700,Utility,1710,Utility,1720,Utility,1730,Utility,1740,Utility,1750,Utility,1760,Utility,1770,Utility,1780,Utility,1790,Utility,1800,Utility,1810,Utility,1820,Utility,1830,Public,1840,Utility,1850,Utility,1860,Utility,1870,Agricultural,1880,Agricultural,1890,Agricultural,1900,Agricultural,1910,Residential,1920,Residential,1930,Agricultural,1940,Agricultural,1950,Agricultural,1960,Public,1970,Public,1980,Assembly,1990,Assembly,2000,Service,2010,Service,2020,Public,2030,Service,2040,Public,2050,Public,2060,Public,2070,Educational,2080,Educational,2090,Educational,2100,Educational,2110,Educational,2120,Other,2130,Other,2140,Public,2150,Public,2160,Public,2170,Other,2180,Public,2190,Public,2200,Other,2210,Assembly,2220,Assembly,2230,Assembly,2240,Assembly,2250,Public,2260,Assembly,2270,Assembly,2280,Assembly,2290,Assembly,2300,Public,2310,Public,2320,Public,2330,Public,2340,Public,2350,Public,2360,Public,2370,Public,2380,Public,2390,Public,2400,Service,2410,Service,2420,Other,2430,Other,2440,Other,2450,Other,2460,Other,2470,Other,2480,Transport,2490,Transport,2500,Transport,2510,Transport,2520,Transport,2530,Transport,2540,Transport,2550,Public,2560,Public,2570,Public,2580,Public,2590,Public,2600,Public,2610,Public,2620,Agricultural,2630,Agricultural,2640,Other,2650,Service,2700,Other
    SRC = citygml_usage
    -> AttributeValueMapper_5
Note: roofForm
AttributeValueMapper_5
    DIRECTION = Forward (Source To Destination)
    VAL_ATTR = roofForm
    DEFAULT_VALUE = Other
    LUT = 1000,Flat,1010,Mono-pitch,1020,Mono-pitch,1030,Gable,1040,Hip,1050,Hip,1060,Mansard,1070,Pyramid,1080,Conical,1090,Domical,1100,Shed,1110,Arched,1120,Pyramid,1130,Complex
    SRC = citygml_roof_type
    -> TestFilter_3
TestFilter_3
    TEST_LIST = BOOL_OP,OR,COMPOSITE_TEST,<Unused>,TEST_CLAUSE,"TEST @Value(fme_feature_type) = Building",Building,BOOL_OP,OR,COMPOSITE_TEST,<Unused>,TEST_CLAUSE,"TEST @Value(fme_feature_type) = BuildingPart",BuildingPart
    DEFAULT_VALUE = <UNFILTERED>
    BuildingPart -> AttributeRenamer_4
    Building -> Building (output)
Building (output)
AttributeRenamer_4
    ATTR_LIST = BuildingFID,BuildingShellFID,""
    -> BuildingPart (output)
BuildingPart (output)
AttributeKeeper_3
    KEEP_ATTRS = gml_id,gml_parent_id,description,name,citygml_usage,citygml_function,citygml_class,type,FID,attribution
    -> AttributeRenamer_7
AttributeRenamer_7
    ATTR_LIST = FID,BuildingShellPartFID,""
    -> BulkAttributeRenamer_2
BulkAttributeRenamer_2
    REPLACE_STR = BoundarySurface_
    ATTRCHOICE = All Attributes
    PATTERN_ACTION_DISP = Add String Prefix
    -> BuildingShellPart (output)
BuildingShellPart (output)
AttributeKeeper_4
    KEEP_ATTRS = gml_id,gml_parent_id,description,name,beginLifespan,endLifespan,citygml_usage,citygml_function,citygml_class,type,FID,attribution
    -> AttributeRenamer_5
AttributeRenamer_5
    ATTR_LIST = citygml_usage,spaceUse,"",citygml_function,spaceFunction,"",FID,BuildingInteriorSpaceFID,"","",accessType,unknown
    -> BulkAttributeRenamer_3
BulkAttributeRenamer_3
    REPLACE_STR = Room_
    ATTRCHOICE = All Attributes
    PATTERN_ACTION_DISP = Add String Prefix
    -> Room (output)
Room (output)
AttributeKeeper_5
    KEEP_ATTRS = gml_id,gml_parent_id,description,name,beginLifespan,endLifespan,citygml_usage,citygml_function,citygml_class,fme_feature_type,type,FID,attribution
    -> AttributeRenamer
AttributeRenamer
    ATTR_LIST = FID,BuildingInteriorStructureFID,"","",accessType,unknown
    -> BulkAttributeRenamer_5
BulkAttributeRenamer_5
    REPLACE_STR = Inner_
    ATTRCHOICE = All Attributes
    PATTERN_ACTION_DISP = Add String Prefix
    -> InnerSurfaces (output)
InnerSurfaces (output)
AttributeKeeper_6
    KEEP_ATTRS = gml_id,gml_parent_id,description,name,beginLifespan,endLifespan,citygml_usage,citygml_function,citygml_class,type,FID,attribution
    -> AttributeRenamer_6
AttributeRenamer_6
    ATTR_LIST = FID,BuildingInteriorStructureFID,"","",accessType,unknown
    -> Deaggregator
Deaggregator
    LIST_ATTR_MODE_LOOKUP = LEAN
    MODE = Flatten One Level
    SPLIT_COMPOSITES = No
    PART_NUMBER_FIELD = _part_number
    EXPLODE_INSTANCES = No
    GEOM_NAME_FIELD = _geometry_name
    DEAGGREGATED -> GeometryCoercer_3
GeometryCoercer_3
    CHECKZ = No
    KIND = fme_polygon
    COERCED -> Opening (output)
Opening (output)
AttributeKeeper_2
    KEEP_LIST = citygml_address{}
    KEEP_ATTRS = gml_parent_id,citygml_address,attribution
    -> Address (output)
Address (output)
AttributeCreator_2
    ATTR_LIST = position,"FME_CONDITIONAL:DEFAULT_VALUE'Unknown'BOOL_OP;OR;COMPOSITE_TEST;<Unused>;TEST @Value(fme_feature_type) = IntBuildingInstallation'Interior'BOOL_OP;OR;COMPOSITE_TEST;<Unused>;TEST @Value(fme_feature_type) = BuildingInstallation'Exterior'BOOL_OP;OR;COMPOSITE_TEST;<Unused>;TEST @Value(fme_feature_type) = BuildingFurniture'Interior'FME_NUM_CONDITIONS4___"
    -> AttributeKeeper_7
AttributeKeeper_7
    KEEP_ATTRS = gml_id,gml_parent_id,citygml_feature_role,description,name,beginLifespan,endLifespan,citygml_usage,citygml_function,citygml_class,type,FID,attribution,position
    -> AttributeRenamer_8
AttributeRenamer_8
    ATTR_LIST = FID,BuildingInstallationFID,"",citygml_feature_role,subtype,""
    -> FeatureTypeFilter_3
FeatureTypeFilter_3
    ATTRIBUTES = <BLANK>,<UNFILTERED>,BuildingFurniture,BuildingInstallation,IntBuildingInstallation
    BuildingFurniture -> BuildingFurniture (output)
    IntBuildingInstallation -> IntBuildingInstallation (output)
    BuildingInstallation -> BuildingInstallation (output)
BuildingFurniture (output)
BuildingInstallation (output)
IntBuildingInstallation (output)
ClosureSurface (output)

FME custom transformer GroundSurfaceExtractor

Parameters:
- FME_PROCESS_GROUP_BY =   # " " Parallel Process By

Building (input)
    -> AttributeCreator
Sampler_SAMPLED_183 (output)

Bookmark: Find BuildingFootprint
AttributeCreator
    ATTR_LIST = currentZMax,"",footPrintZ,""
    -> VariableSetter_2
VariableSetter_2
    SCOPE = Local
    VALUE = 9999
    VARNAME = currentZMax
    -> GeometryCoercer_2
GeometryCoercer_2
    KIND = fme_composite_surface
    COERCED -> Deaggregator_4
Deaggregator_4
    LIST_ATTR_MODE_LOOKUP = LEAN
    MODE = Flatten One Level
    SPLIT_COMPOSITES = Yes
    PART_NUMBER_FIELD = _part_number
    EXPLODE_INSTANCES = No
    GEOM_NAME_FIELD = _geometry_name
    DEAGGREGATED -> BoundsExtractor
BoundsExtractor
    YMIN = _ymin
    ZMIN = _zmin
    XMIN = _xmin
    XMAX = _xmax
    ZMAX = _zmax
    YMAX = _ymax
    -> GeometryCoercer
GeometryCoercer
    CHECKZ = No
    KIND = fme_polygon
    COERCED -> VariableRetriever
VariableRetriever
    SCOPE = Local
    VARNAME = currentZMax
    VALUE_ATTR = currentZMax
    -> Tester
Tester
    TEST_MODE = Automatic
    TEST_DESCRIPTION = ""
    BOOL_OP = OR
    TEST_CLAUSE = TEST @Value(_zmax) < @Value(currentZMax)
    PASSED -> VariableSetter
    FAILED -> FeatureHolder
VariableSetter
    SCOPE = Local
    VALUE = @Value(_zmax)
    VARNAME = currentZMax
    -> FeatureHolder
FeatureHolder
    -> VariableRetriever_2
VariableRetriever_2
    SCOPE = Local
    VARNAME = currentZMax
    VALUE_ATTR = footPrintZ
    -> Tester_2
Tester_2
    TEST_MODE = Automatic
    TEST_DESCRIPTION = ""
    BOOL_OP = OR
    TEST_CLAUSE = TEST @Value(_zmax) = @Value(footPrintZ)
    PASSED -> Dissolver
Dissolver
    NO_OVRLP = No
    ACCUM_INPUT_ATTRS = Yes
    AREA -> Sampler_SAMPLED_183 (output)
    <REJECTED> -> Sampler_SAMPLED_183 (output)
