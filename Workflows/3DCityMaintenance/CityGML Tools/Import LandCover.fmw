FME workspace Import LandCover.fmw

Parameters:
- SourceDataset_CITYGML_4 =   # Source CityGML File(s)
- CITYGML_IN_SRS_AXIS_ORDER_CITYGML =   # GML SRS Axis Order
- DestDataset_GEODATABASE_FILE =   # Destination Esri File Geodatabase
- GEODATABASE_FILE_OUT_TEMPLATEFILE_GEODATABASE_FILE =   # XML Workspace Document (for initial creation of Geodatabase schema)
- GEODATABASE_FILE_OUT_OVERWRITE_GEODB_GEODATABASE_FILE = No   # Overwrite Existing Geodatabase

Readers:
- CITYGML_1: CITYGML from $(SourceDataset_CITYGML_4)

Writers:
- GEODATABASE_FILE_1: GEODATABASE_FILE to $(DestDataset_GEODATABASE_FILE)

Window (reader CITYGML_1)
    attributes: citygml_target_uri xml_buffer, citygml_feature_role_attr_name xml_buffer, citygml_feature_role_attr_val xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_interior_hollow_space{}.xlink_href xml_buffer, citygml_target{} xml_buffer, citygml_consists_of_building_part{}.xlink_href xml_buffer, citygml_interior_bridge_room{}.xlink_href xml_buffer, citygml_parent_xlink_href xml_buffer, citygml_bridge_room_installation{}.xlink_href xml_buffer, citygml_species_codeSpace xml_buffer, citygml_group_member{}.role xml_buffer, citygml_outer_tunnel_installation{}.xlink_href xml_buffer, citygml_traffic_area{}.xlink_href xml_buffer, citygml_interior_building_installation{}.xlink_href xml_buffer, citygml_consists_of_bridge_part{}.xlink_href xml_buffer, citygml_surface_material_codeSpace xml_buffer, citygml_group_member{}.xlink_href xml_buffer, citygml_room_installation{}.xlink_href xml_buffer, citygml_outer_bridge_installation{}.xlink_href xml_buffer, citygml_bounded_by{}.xlink_href xml_buffer, citygml_water_level_codeSpace xml_buffer, citygml_class_codeSpace xml_buffer,
      citygml_relief_component{}.xlink_href xml_buffer, citygml_interior_room{}.xlink_href xml_buffer, citygml_surface_data_member{}.xlink_href xml_buffer, citygml_hollow_space_installation{}.xlink_href xml_buffer, citygml_opening{}.xlink_href xml_buffer, citygml_city_object_member{}.xlink_href xml_buffer, citygml___generic_application_property_of_bridge_construction_element{} xml_xml, citygml_outer_building_installation{}.xlink_href xml_buffer, citygml_interior_tunnel_installation{}.xlink_href xml_buffer, citygml_interior_bridge_installation{}.xlink_href xml_buffer, citygml_mime_type_codeSpace xml_buffer, citygml_auxiliary_traffic_area{}.xlink_href xml_buffer, gml_feature_member{}.xlink_href xml_buffer, citygml_interior_furniture{}.xlink_href xml_buffer, citygml_consists_of_tunnel_part{}.xlink_href xml_buffer, citygml_outer_bridge_construction{}.xlink_href xml_buffer, citygml_address{}.xlink_href xml_buffer, citygml_appearance_member{}.xlink_href xml_buffer, citygml_is_movable xml_boolean, citygml_roof_type_codeSpace xml_buffer
    -> FeatureTypeFilter_2
Note: create FID
AttributeCreator_5
    ATTR_LIST = FID,@Value(fme_feature_type)/@Value(type)/@Count(@Value(fme_feature_type))/1
    -> AttributeRenamer_2
Note: general attribute mapping
AttributeRenamer_2
    ATTR_LIST = gml_name,name,"",gml_description,description,""
    -> GeometryPropertyExtractor
AttributeCopier_2
    ATTR_LIST = primaryLandcoverSubType,citygml_class,primaryLandcoverType,type
    -> AttributeRenamer_4
AttributeRenamer_4
    ATTR_LIST = FID,LandCoverFID,""
    -> FeatureTypeFilter
FeatureTypeFilter
    ATTRIBUTES = <BLANK>,<UNFILTERED>,PlantCover,WaterBody,WaterSurface,WaterGroundSurface,WaterClosureSurface,TrafficArea,AuxiliaryTrafficArea
    WaterBody -> BulkAttributeRenamer
    PlantCover -> TestFilter
    TrafficArea -> TestFilter
    AuxiliaryTrafficArea -> TestFilter
    PlantCover -> AttributeRenamer_3
    TrafficArea -> AttributeRenamer_3
    AuxiliaryTrafficArea -> AttributeRenamer_3
    WaterBody -> AttributeRenamer_3
    WaterSurface -> FeatureMerger_3 [input 1]
    WaterGroundSurface -> FeatureMerger_3 [input 1]
    WaterClosureSurface -> FeatureMerger_3 [input 1]
AttributeRenamer_3
    ATTR_LIST = LandCoverFID,referenceFID,""
    -> GeometryFilter
LandCover (writer GEODATABASE_FILE_1)
    attributes: LandCoverFID char(50), name char(100), description char(250), attribution char(250), primaryLandcoverType char(50), primaryLandcoverSubType char(50), secondaryLandcoverType char(50), secondaryLandcoverSubType char(50), density double, verticalExtent double

Bookmark: set type attribute
FeatureTypeFilter_2
    ATTRIBUTES = <BLANK>,<UNFILTERED>,WaterClosureSurface,PlantCover,WaterSurface,WaterBody,WaterGroundSurface,TrafficArea,AuxiliaryTrafficArea
    PlantCover -> AttributeValueMapper_4
    WaterSurface -> AttributeValueMapper_5
    WaterBody -> AttributeValueMapper_5
    WaterGroundSurface -> AttributeValueMapper_5
    TrafficArea -> AttributeValueMapper_2
    AuxiliaryTrafficArea -> AttributeValueMapper_3
    WaterClosureSurface -> AttributeCreator
AttributeCreator
    ATTR_LIST = type,Unknown
    -> AttributeCreator_5
AttributeValueMapper_4
    DIRECTION = Forward (Source To Destination)
    VAL_ATTR = type
    DEFAULT_VALUE = Other
    LUT = 1010,Wetland,1020,Barren,1030,Barren,1040,Barren,1050,Barren,1060,Shrub,1070,Barren,1080,Barren,1090,Barren,1100,Barren,1110,Barren,1120,Barren,1130,Wetland,1140,Wetland,1150,Wetland,1160,Wetland,1170,Barren,1180,Barren,1190,Barren,1200,Barren,1210,Barren,1220,Barren,1230,Wetland,1240,Barren,1250,Barren,1260,Barren,1270,Barren,1280,Barren,1290,Barren,1300,Wetland,1310,Barren,1320,Barren,1330,Barren,1340,Barren,1350,Barren,1360,Wetland,1370,Barren,1380,Barren,1390,Forest,1400,Forest,1410,Forest,1420,Forest,1430,Barren,1440,Barren,1450,Barren,1460,Barren,1470,Barren,1480,Shrub,1490,Shrub,1500,Shrub,1510,Forest,1520,Forest,9999,Barren
    SRC = citygml_class
    -> AttributeCreator_5
AttributeValueMapper_5
    DIRECTION = Forward (Source To Destination)
    VAL_ATTR = type
    DEFAULT_VALUE = Other
    LUT = 1000,Water,1010,Water,1020,Water,1030,Water,1040,Water,1050,Water,1060,Lake,1070,Water,1080,Water,1090,Water,1100,Water,1110,Wetland,1120,Water,1130,Water,1140,Wetland,1150,Water,1160,Water,1170,Water,1180,Water,1190,Water,1200,Water,1210,Water,1220,Water,1230,Water,1240,Water,1250,Water,1260,Water,9999,Water
    SRC = citygml_class
    -> AttributeCreator_5
AttributeValueMapper_2
    DIRECTION = Forward (Source To Destination)
    VAL_ATTR = type
    DEFAULT_VALUE = Other
    LUT = 1,Developed,10,Developed,11,Developed,12,Developed,13,Developed,14,Developed,15,Developed,16,Developed,17,Developed,18,Developed,19,Developed,2,Developed,20,Developed,21,Developed,22,Developed,23,Developed,24,Developed,25,Developed,26,Developed,27,Developed,28,Developed,29,Developed,3,Developed,30,Developed,31,Developed,32,Developed,33,Developed,34,Developed,35,Developed,36,Developed,37,Developed,4,Developed,5,Developed,6,Developed,7,Developed,8,Developed,9,Developed,9999,Developed
    SRC = citygml_function
    -> AttributeCreator_5
AttributeValueMapper_3
    DIRECTION = Forward (Source To Destination)
    VAL_ATTR = type
    DEFAULT_VALUE = Other
    LUT = 1000,Developed,1010,Developed,1020,Developed,1030,Developed,1040,Developed,1100,Developed,1200,Developed,1210,Developed,1220,Developed,1230,Developed,1300,Developed,1400,Developed,1410,Developed,1420,Developed,1430,Developed,1440,Developed,1500,Developed,1600,Developed,1700,Developed
    SRC = citygml_function
    -> AttributeCreator_5

Bookmark: attribution
  store CityGML filename + feature type + geometry_name
GeometryPropertyExtractor
    TRAIT_ATTR_LIST = citygml_lod_name
    GQUERY:
      for $geom in //geometry
      where $geom/count(parent::geometry) = 0
      return number($geom/@fme_id)
    PREFIX_EXTRACTED_TRAITS = No
    EXTRACTTYPE_PARAM = Traits
    EXTRACTED -> StringConcatenator_2
    UNTOUCHED -> StringConcatenator_2
StringConcatenator_2
    PARM_LINE = @Value(fme_basename)/@Value(fme_feature_type)/@Value(citygml_lod_name)
    VAL_ATTR = attribution
    -> PythonCaller

Bookmark: AttributeContainer handling (all attributes not explicitly mapped)
PythonCaller
    PYTHONSOURCE:
      from fmeobjects import FMEFeature
      from re import match

      # Template Class Interface:
      class FeatureProcessor(object):

          def __init__(s):
              #,"citygml_measured_height"
              s.DoNotMapList =[
                  "^fme_.*",
                  "name","xml_type","attribution","citygml_feature_role","citygml_level_of_detail{0}","FID",
                  "description","type","gml_parent_id",
                  "citygml_roof_type","citygml_storeys_above_ground",
                  "citygml_storeys_below_ground",
                  "_geometry_name","multi_reader_full_id","multi_reader_id",
                  "multi_reader_type","multi_reader_keyword",
                  "citygml_target_uri"]


          def input(s,f):
              #get FeatureType
              fType = f.getAttribute("fme_feature_type")

              if fType == "CityModel":
                  return
              #get AllAttributes
              allAttr = f.getAllAttributeNames()

              ### Nur Attribute, die nicht auf die DoNotMapListe matchen
              for a in filter(lambda x: not any(match(regex,x) for regex in s.DoNotMapList), allAttr):
                  aValue = f.getAttribute(a)
                  #if aValue is None or aValue == "" or aValue is u"":
                  if not aValue:
                      next
                  #New AttributeContainer Feature
                  nF = FMEFeature()
                  #containerFeature.setFeatureType("AttributeContainer")
                  nF.setAttribute("isAttributeContainer","True")
                  #print a
                  nF.setAttribute("path",a)
                  nF.setAttribute("type",0)
                  nF.setAttribute("value",aValue)
                  nF.setAttribute("referenceFID",f.getAttribute("FID"))
                  nF.setAttribute("referenceType",fType)
                  s.pyoutput(nF)

              s.pyoutput(f)

          def close(s):
              pass
    PYTHONSYMBOL = FeatureProcessor
    NEW_ATTRIBUTES = fme_feature_type isAttributeContainer referenceFID referenceType path value type
    -> Tester_2
Tester_2
    TEST_MODE = Automatic
    TEST_DESCRIPTION = ""
    BOOL_OP = OR
    TEST_CLAUSE = TEST @Value(isAttributeContainer) = True
    FAILED -> AttributeKeeper
    PASSED -> AttributeContainer (writer GEODATABASE_FILE_1)
AttributeContainer (writer GEODATABASE_FILE_1)
    attributes: path char(250), type char(30), value char(250), referenceFID char(50), referenceType char(50)
AttributeKeeper
    KEEP_LIST = citygml_address{}
    KEEP_ATTRS = gml_id,gml_parent_id,citygml_feature_role,description,name,beginLifespan,endLifespan,citygml_address,citygml_height_units,citygml_measured_height,citygml_usage,citygml_function,citygml_year_of_demolition,citygml_height,citygml_year_of_construction,citygml_class,fme_feature_type,type,FID,citygml_lod_name,attribution
    -> AttributeCopier_2

Bookmark: Water
BulkAttributeRenamer
    REPLACE_STR = WaterBody_
    ATTRCHOICE = All Attributes
    PATTERN_ACTION_DISP = Add String Prefix
    -> FeatureMerger_3 [input 2]
FeatureMerger_3
    PROCESS_DUPS = Yes
    MERGE_TYPE = Attributes Only
    GEOM_TYPE = Build Polygons
    SUPPLIERS_FIRST = No
    JOIN_KEYS = @Value(gml_parent_id) @Value(WaterBody_gml_id)
    UNREFERENCED -> BulkAttributeRenamer_2
    NOT_MERGED -> AttributeRenamer_3
    NOT_MERGED -> Tester
    MERGED -> AttributeRenamer
    MERGED -> AttributeKeeper_2
AttributeRenamer
    ATTR_LIST = WaterBody_LandCoverFID,LandCoverFID,""
    -> AttributeRenamer_3
AttributeKeeper_2
    KEEP_ATTRS = fme_feature_type,_WaterSurfaceGeometry,WaterBody_gml_id,WaterBody_gml_parent_id,WaterBody_citygml_feature_role,WaterBody_description,WaterBody_name,WaterBody_citygml_address,WaterBody_citygml_height_units,WaterBody_citygml_measured_height,WaterBody_citygml_usage,WaterBody_citygml_function,WaterBody_citygml_year_of_demolition,WaterBody_citygml_height,WaterBody_citygml_year_of_construction,WaterBody_citygml_class,WaterBody_primaryLandcoverSubType,WaterBody_type,WaterBody_primaryLandcoverType,WaterBody_LandCoverFID,WaterBody_citygml_lod_name,WaterBody_attribution
    -> BulkAttributeRenamer_3
BulkAttributeRenamer_3
    REPLACE_STR = WaterBody_
    ATTRCHOICE = All Attributes
    PATTERN_ACTION_DISP = Remove Prefix String
    CASE_DISP = yes
    -> Tester
Note: if WaterSurface
Tester
    TEST_MODE = Automatic
    TEST_DESCRIPTION = ""
    BOOL_OP = OR
    TEST_CLAUSE = TEST @Value(fme_feature_type) = WaterSurface
    PASSED -> LandCover_Polygon_Replacer
    FAILED -> Tester_3
LandCover_Polygon_Replacer: FootPrintReplacer
    Aggregator_4_AGGREGATE_69 -> LandCover (writer GEODATABASE_FILE_1)
Note: if WaterGroundSurface
Tester_3
    TEST_MODE = Automatic
    TEST_DESCRIPTION = ""
    BOOL_OP = OR
    TEST_CLAUSE = TEST @Value(fme_feature_type) = WaterSurface
    PASSED -> LandCover_Polygon_Replacer_2
    FAILED -> Tester_4
Note: if WaterClosureSurface
Tester_4
    TEST_MODE = Automatic
    TEST_DESCRIPTION = ""
    BOOL_OP = OR
    TEST_CLAUSE = TEST @Value(fme_feature_type) = WaterClosureSurface
    PASSED -> LandCover_Polygon_Replacer_2
LandCover_Polygon_Replacer_2: FootPrintReplacer
    Aggregator_4_AGGREGATE_69 -> LandCover (writer GEODATABASE_FILE_1)
BulkAttributeRenamer_2
    REPLACE_STR = WaterBody_
    ATTRCHOICE = All Attributes
    PATTERN_ACTION_DISP = Remove Prefix String
    CASE_DISP = yes
    -> Extract_LandCover_Polygon
Note: Extract LandCover Polygon
Extract_LandCover_Polygon: GroundSurfaceExtractor
    Sampler_SAMPLED_183 -> LandCover (writer GEODATABASE_FILE_1)

Bookmark: store original geometries
GeometryFilter
    BREAK_AGG = No
    SURFACE -> StringConcatenator
    SOLID -> StringConcatenator
    LINE -> StringConcatenator_3
    ARC -> StringConcatenator_3
StringConcatenator_3
    PARM_LINE = SpatialLineAnnotation/@Value(type)/@Count(SpatialLineAnnotation)/1
    VAL_ATTR = SpatialVolumeAnnotationFID
    -> SpatialLineAnnotation (writer GEODATABASE_FILE_1)
SpatialLineAnnotation (writer GEODATABASE_FILE_1)
    attributes: geodb_oid integer, OBJECTID integer, SpatialLineAnnotationFID char(50), name char(100), description char(250), attribution char(250), referenceFID char(50), value char(250), type char(50), subtype char(50), beginLifespan date, endLifespan date, Shape_Length double
StringConcatenator
    PARM_LINE = SpatialVolumeAnnotation/@Value(type)/@Count(SpatialVolumeAnnotation)/1
    VAL_ATTR = SpatialVolumeAnnotationFID
    -> SpatialVolumeAnnotation (writer GEODATABASE_FILE_1)
SpatialVolumeAnnotation (writer GEODATABASE_FILE_1)
    attributes: SpatialVolumeAnnotationFID char(50), name char(100), description char(250), attribution char(250), referenceFID char(50), value char(250), type char(50), subtype char(50), beginLifespan date, endLifespan date

Bookmark: PlantCover and TrafficArea
TestFilter
    TEST_LIST = BOOL_OP,OR,COMPOSITE_TEST,<Unused>,TEST_CLAUSE,"TEST @Value(citygml_lod_name) MATCHES_REGEX lod[1-4]MultiSurface",MultiSurface,BOOL_OP,OR,COMPOSITE_TEST,<Unused>,TEST_CLAUSE,"TEST @Value(citygml_lod_name) MATCHES_REGEX lod[1-4]MultiSolid",MultiSolid
    DEFAULT_VALUE = <UNFILTERED>
    MultiSurface -> LandCover_Polygon_Replacer_3
    MultiSolid -> Extract_LandCover_Polygon_2
LandCover_Polygon_Replacer_3: FootPrintReplacer
    Aggregator_4_AGGREGATE_69 -> LandCover (writer GEODATABASE_FILE_1)
Note: Extract LandCover Polygon
Extract_LandCover_Polygon_2: GroundSurfaceExtractor
    Sampler_SAMPLED_183 -> LandCover (writer GEODATABASE_FILE_1)

FME custom transformer FootPrintReplacer

Parameters:
- FME_PROCESS_GROUP_BY =   # " " Parallel Process By

Aggregator_6_INPUT_66 (input)
    -> Aggregator_6
Aggregator_6
    GROUP_BY = $(FME_PROCESS_GROUP_BY)
    MODE = Assemble One Level
    ACCUM_ATTRS_NAME = Yes
    SEP = ,
    AGGREGATE_TYPE = Homogeneous Collection (If Possible)
    ORDERED = No
    AGGREGATE -> BoundsExtractor_2
BoundsExtractor_2
    YMIN = _ymin
    ZMIN = _zmin
    XMIN = _xmin
    XMAX = _xmax
    ZMAX = _zmax
    YMAX = _ymax
    -> Deaggregator_6
Deaggregator_6
    LIST_ATTR_MODE_LOOKUP = LEAN
    MODE = Flatten All Levels
    SPLIT_COMPOSITES = No
    EXPLODE_INSTANCES = No
    GEOM_NAME_FIELD = _geometry_name
    DEAGGREGATED -> GeometryCoercer_6
GeometryCoercer_6
    CHECKZ = No
    KIND = fme_polygon
    COERCED -> 3DForcer
3DForcer
    ZVALATTR = @Value(_zmin)
    -> Dissolver_2
Dissolver_2
    GROUP_BY = $(FME_PROCESS_GROUP_BY)
    NO_OVRLP = No
    ACCUM_INPUT_ATTRS = Yes
    AREA -> Aggregator_4
    <REJECTED> -> Aggregator_4
Aggregator_4
    GROUP_BY = $(FME_PROCESS_GROUP_BY)
    MODE = Assemble One Level
    ACCUM_ATTRS_NAME = Yes
    SEP = ,
    AGGREGATE_TYPE = Homogeneous Collection (If Possible)
    ORDERED = No
    AGGREGATE -> AreaCalculator
AreaCalculator
    AREA_ATTR = _area
    AREA_TYPE = Plane Area
    MULT = 1
    -> Aggregator_4_AGGREGATE_69 (output)
Aggregator_4_AGGREGATE_69 (output)

FME custom transformer GroundSurfaceExtractor

Parameters:
- FME_PROCESS_GROUP_BY =   # " " Parallel Process By

Building (input)
    -> AttributeCreator
Sampler_SAMPLED_183 (output)

Bookmark: Find BuildingFootprint
AttributeCreator
    ATTR_LIST = currentZMax,"",footPrintZ,""
    -> VariableSetter_2
VariableSetter_2
    SCOPE = Local
    VALUE = 9999
    VARNAME = currentZMax
    -> GeometryCoercer_2
GeometryCoercer_2
    KIND = fme_composite_surface
    COERCED -> Deaggregator_4
Deaggregator_4
    LIST_ATTR_MODE_LOOKUP = LEAN
    MODE = Flatten All Levels
    SPLIT_COMPOSITES = Yes
    EXPLODE_INSTANCES = No
    GEOM_NAME_FIELD = _geometry_name
    DEAGGREGATED -> BoundsExtractor
BoundsExtractor
    YMIN = _ymin
    ZMIN = _zmin
    XMIN = _xmin
    XMAX = _xmax
    ZMAX = _zmax
    YMAX = _ymax
    -> GeometryCoercer
GeometryCoercer
    CHECKZ = No
    KIND = fme_polygon
    COERCED -> VariableRetriever
VariableRetriever
    SCOPE = Local
    VARNAME = currentZMax
    VALUE_ATTR = currentZMax
    -> Tester
Tester
    TEST_MODE = Automatic
    TEST_DESCRIPTION = ""
    BOOL_OP = OR
    TEST_CLAUSE = TEST @Value(_zmax) < @Value(currentZMax)
    PASSED -> VariableSetter
    FAILED -> FeatureHolder
VariableSetter
    SCOPE = Local
    VALUE = @Value(_zmax)
    VARNAME = currentZMax
    -> FeatureHolder
FeatureHolder
    -> VariableRetriever_2
VariableRetriever_2
    SCOPE = Local
    VARNAME = currentZMax
    VALUE_ATTR = footPrintZ
    -> Tester_2
Tester_2
    TEST_MODE = Automatic
    TEST_DESCRIPTION = ""
    BOOL_OP = OR
    TEST_CLAUSE = TEST @Value(_zmax) = @Value(footPrintZ)
    PASSED -> Dissolver
Dissolver
    NO_OVRLP = No
    ACCUM_INPUT_ATTRS = No
    AREA -> Sampler_SAMPLED_183 (output)
    <REJECTED> -> Sampler_SAMPLED_183 (output)
