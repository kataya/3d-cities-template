FME workspace Export SolitaryVegetationObject.fmw

Parameters:
- SourceDataset_GEODATABASE_FILE =   # Source Esri File Geodatabase
- DestDataset_CITYGML =   # Destination CityGML Document
- citygml_version = 1.0   # CityGML Version
- CityModel_name = 3DCIM CityModel Export   # CityModel Name (gml:name)
- Citymodel_description = 3DCIM CityModel Export   # CityModel description (gml:description)

Readers:
- GEODATABASE_FILE_1: GEODATABASE_FILE from $(SourceDataset_GEODATABASE_FILE)

Writers:
- CITYGML_1: CITYGML to $(DestDataset_CITYGML)

Bookmark: CityModel
Creator_2
    NUM = 1
    GEOMTYPE = Geometry Object
    CREATED -> AttributeCreator_6
AttributeCreator_6
    ATTR_LIST = gml_name,$(CityModel_name),gml_description,$(Citymodel_description)
    -> CityModel (writer CITYGML_1)
CityModel (writer CITYGML_1)

Bookmark: Tree - SolitaryVegetationObject
Tree (reader GEODATABASE_FILE_1)
    attributes: geodb_oid integer, OBJECTID integer, TreeFID char(50), name char(100), description char(250), attribution char(250), type coded_domain(TreeGenusType:char(50):Abies:Abies:Acacia:Acacia:Acer:Acer:Aesculus:Aesculus:Ailanthus:Ailanthus:Albizia:Albizia:Alnus:Alnus:Amelanchier:Amelanchier:Aralia:Aralia:Arbutus:Arbutus:Asimina:Asimina:Betula:Betula:Calocedrus:Calocedrus:Carpinus:Carpinus:Carya:Carya:Castanea:Castanea:Casuarina:Casuarina:Celtis:Celtis:Cephalanthus:Cephalanthus:Cercis:Cercis:Cercocarpus:Cercocarpus:Chamaecyparis:Chamaecyparis:Chilopsis:Chilopsis:Chrysolepis:Chrysolepis:Cornus:Cornus:Corylus:Corylus:Crataegus:Crataegus:Cupressus:Cupressus:Cyrilla:Cyrilla:Diospyros:Diospyros:Elaeagnus:Elaeagnus:Eucalyptus:Eucalyptus:Fagus:Fagus:Frangula:Frangula:Fraxinus:Fraxinus:Fremontodendron:Fremontodendron:Gleditsia:Gleditsia:Gordonia:Gordonia:Hamamelis:Hamamelis:Ilex:Ilex:Juglans:Juglans:Juniperus:Juniperus:Larix:Larix:Ligustrum:Ligustrum:Liquidambar:Liquidambar:Liriodendron:Liriodendron:Lithocarpus:Lithocarpus:Maclura:Maclura:Magnolia:Magnolia:Melaleuca:Melaleuca:Melia:Melia:Morus:Morus:Myrica:Myrica:Nyssa:Nyssa:Ostrya:Ostrya:Oxydendrum:Oxydendrum:Parkinsonia:Parkinsonia:Paulownia:Paulownia:Persea:Persea:Picea:Picea:Pinus:Pinus:Platanus:Platanus:Populus:Populus:Prosopis:Prosopis:Prunus:Prunus:Pseudotsuga:Pseudotsuga:Purshia:Purshia:Quercus:Quercus:Rhamnus:Rhamnus:Rhododendron:Rhododendron:Rhus:Rhus:Robinia:Robinia:Sabal:Sabal:Salix:Salix:Sambucus:Sambucus:Sapindus:Sapindus:Sassafras:Sassafras:Schefflera:Schefflera:Schinus:Schinus:Sequoiadendron:Sequoiadendron:Sequoia:Sequoia:Serenoa:Serenoa:Shepherdia:Shepherdia:Sophora:Sophora:Sorbus:Sorbus:Spartium:Spartium:Tamarix:Tamarix:Taxus:Taxus:Taxodium:Taxodium:Thuja:Thuja:Tilia:Tilia:Torreya:Torreya:Triadica:Triadica:Tsuga:Tsuga:Ulmus:Ulmus:Umbellularia:Umbellularia:Ungnadia:Ungnadia:Vaccinium:Vaccinium:Washingtonia:Washingtonia:Yucca:Yucca:Other:Other:Unknown:Unknown), type_resolved char(254), subtype char(50), beginLifespan date, endLifespan date, datePlanted date, height double, diameter double, diameterBreastHeight double, canopyShape coded_domain("TreeCanopyShape:char(30):Cylinder:""Cylinder (S1)"":""Rounded Edge Cylinder"":""Rounded Edge Cylinder (S2)"":""Elongated Spheroid"":""Elongated Spheroid (S3)"":Spheroid:""Spheroid (S4)"":""Expanded Paraboloid"":""Expanded Paraboloid (S5)"":Paraboloid:""Paraboloid (S6)"":""Fat Cone"":""Fat Cone (S7)"":Cone:""Cone (S8)"":Neiloid:""Neiloid (S9)"":""Thin Neiloid"":""Thin Neiloid (S10)"":Spreading:""Spreading (S11)"":Other:Other:Unknown:Unknown"), canopyShape_resolved char(254)
    -> GeometryRemover
GeometryRemover
    -> FeatureMerger_2 [input 1]
SpatialVolumeAnnotation (reader GEODATABASE_FILE_1)
    attributes: geodb_oid integer, OID integer, SpatialVolumeAnnotationFID char(50), name char(100), description char(250), attribution char(250), referenceFID char(50), value char(250), type coded_domain("AnnotationType:char(50):Comment:Comment:""Process Result"":""Process Result"":Link:Link:Measurement:Measurement"), type_resolved char(254), subtype char(50), beginLifespan date, endLifespan date
    -> FeatureMerger_2 [input 2]
FeatureMerger_2
    PROCESS_DUPS = No
    MERGE_TYPE = Attributes and Geometry
    SUPPLIERS_FIRST = No
    JOIN_KEYS = @Value(TreeFID) @Value(referenceFID)
    MERGED -> FeatureMerger [input 1]
    NOT_MERGED -> FeatureMerger [input 1]
AttributeContainer (reader GEODATABASE_FILE_1)
    attributes: geodb_oid integer, OBJECTID integer, path char(250), type char(30), value char(250), referenceFID char(50), referenceType char(50)
    -> Aggregator
Aggregator
    GROUP_BY = referenceFID
    MODE = Assemble One Level
    ACCUM_ATTRS_NAME = No
    LIST_NAME = _AttributeContainer
    SEP = ,
    AGGREGATE_TYPE = Homogeneous Collection (If Possible)
    ORDERED = No
    AGGREGATE -> ListElementCounter
ListElementCounter
    LIST_NAME = _AttributeContainer{}
    CNT_ATTR = _element_count
    -> FeatureMerger [input 2]
FeatureMerger
    PROCESS_DUPS = No
    MERGE_TYPE = Attributes Only
    SUPPLIERS_FIRST = No
    JOIN_KEYS = @Value(TreeFID) @Value(referenceFID)
    MERGED -> StringReplacer_3
    NOT_MERGED -> StringReplacer_3
Note: replace "/" with "-" for / all attributes used as gml:id / or gml_parent_id
StringReplacer_3
    SRC_ATTRS = TreeFID,referenceFID
    REGEXP = no
    CASE = no
    REPLACE_TEXT = -
    NO_MATCH = _FME_NO_OP_
    FIND_TEXT = /
    -> AttributeCopier
AttributeCopier
    ATTR_LIST = gml_id,TreeFID
    -> PythonCaller
PythonCaller
    PYTHONSOURCE:
      # Template Class Interface:
      class FeatureProcessor(object):
          def __init__(s):
              pass
          def input(s,f):

              for i in range (0,int(f.getAttribute("_element_count"))):
                  path = f.getAttribute("_AttributeContainer{"+str(i)+"}.path")
                  #logger.logMessageString(path)
                  value = f.getAttribute("_AttributeContainer{"+str(i)+"}.value")
                  #logger.logMessageString(path + value)
                  f.setAttribute(path,value)
              s.pyoutput(f)

          def close(self):
              pass
    PYTHONSYMBOL = FeatureProcessor
    NEW_ATTRIBUTES = citygml_class citygml_species citygml_function citygml_usage citygml_height_units citygml_trunk_diameter_units citygml_crown_diameter_units gml_parent_id citygml_feature_role citygml_relativeToTerrain citygml_relativeToWater
    -> AttributeRemover_2
AttributeRemover_2
    LIST_ATTRS = _AttributeContainer{}.type _AttributeContainer{}.referenceType _AttributeContainer{}.referenceFID _AttributeContainer{}.value _AttributeContainer{}.geodb_oid _AttributeContainer{}.path _AttributeContainer{} _AttributeContainer{}.OBJECTID
    -> AttributeRenamer_2
AttributeRenamer_2
    ATTR_LIST = citygml_species,citygml_species_temp,""
    -> AttributeRenamer
AttributeRenamer
    ATTR_LIST = height,citygml_height,"",diameter,citygml_crown_diameter,"",diameterBreastHeight,citygml_trunk_diameter,"",beginLifespan,citygml_creationDate,"",endLifespan,citygml_terminationDate,"",name,gml_name,"",description,gml_description,""
    -> TestFilter
TestFilter
    TEST_LIST = BOOL_OP,OR,COMPOSITE_TEST,<Unused>,TEST_CLAUSE,"TEST citygml_creationDate NOT_ATTRIBUTE_IS_EMPTY <Unused>",creationDate,BOOL_OP,OR,COMPOSITE_TEST,<Unused>,TEST_CLAUSE,"TEST citygml_terminationDate NOT_ATTRIBUTE_IS_EMPTY <Unused>",terminationDate
    DEFAULT_VALUE = <UNFILTERED>
    creationDate -> DateFormatter
    terminationDate -> DateFormatter_2
    <UNFILTERED> -> Tester
DateFormatter
    DATE_ATTR = citygml_creationDate
    FMT = XML Date (%Y-%m-%d)
    -> Tester
DateFormatter_2
    DATE_ATTR = citygml_terminationDate
    FMT = XML Date (%Y-%m-%d)
    -> Tester
Tester
    TEST_MODE = Automatic
    TEST_DESCRIPTION = ""
    BOOL_OP = OR
    TEST_CLAUSE = TEST @Value(type) = Other
    FAILED -> AttributeValueMapper
    PASSED -> AttributeRenamer_3
AttributeRenamer_3
    ATTR_LIST = citygml_species_temp,citygml_species,""
    -> AttributeRemover
AttributeValueMapper
    DIRECTION = Forward (Source To Destination)
    VAL_ATTR = citygml_species
    LUT = Abies,1640,Acer,1090,Aesculus,1930,Ailanthus,1960,Alnus,1060,Aralia,2030,Betula,1050,Calocedrus,2190,Carpinus,2240,Castanea,2260,Celtis,2340,Cercis,2350,Chamaecyparis,2370,Cornus,2440,Corylus,2500,Corylus,5340,Crataegus,2540,Cupressus,2600,Elaeagnus,2650,Fagus,1040,Frangula,2760,Fraxinus,1100,Gleditsia,2820,Hamamelis,2840,Ilex,5900,Juglans,2910,Juniperus,2930,Larix,1020,Ligustrum,3030,Liquidambar,3040,Magnolia,1450,Ostrya,3180,Picea,1000,Pinus,1010,Platanus,3550,Populus,1070,Prunus,6500,Pseudotsuga,3750,Quercus,3810,Rhamnus,3960,Rhododendron,6660,Rhus,3990,Robinia,4020,Salix,1080,Sambucus,4160,Sequoia,4190,Sequoiadendron,4200,Ulmus,7090,Unknown,9999,Vaccinium,7110
    SRC = type
    -> AttributeRemover
AttributeRemover
    LIST_ATTRS = attributionParts{} _AttributeContainer{}.type _AttributeContainer{}.referenceType _AttributeContainer{}.referenceFID _AttributeContainer{}.value _AttributeContainer{}.geodb_oid _AttributeContainer{}.path _AttributeContainer{} _AttributeContainer{}.OBJECTID
    REMOVE_ATTRS = citygml_species_temp
    -> CustomNullAttributeRemover_2
CustomNullAttributeRemover_2
    SRC_ATTRS = _element_count,geodb_oid,OBJECTID,TreeFID,gml_id,attribution,type,type_resolved,subtype,datePlanted,canopyShape,canopyShape_resolved,path,value,referenceFID,referenceType,citygml_class,citygml_function,citygml_usage,citygml_height_units,citygml_trunk_diameter_units,citygml_crown_diameter_units,gml_parent_id,citygml_feature_role,citygml_relativeToTerrain,citygml_relativeToWater,OID,SpatialVolumeAnnotationFID
    -> AttributeSplitter
AttributeSplitter
    LIST_NAME = attributionParts
    ATTR_NAME = attribution
    DELIMITER = /
    TRIM_OPTION = Both
    DROP_EMPTY_PARTS = No
    -> AttributeCreator
AttributeCreator
    ATTR_LIST = citygml_lod_name,@Value(attributionParts{2})
    -> StringReplacer
StringReplacer
    SRC_ATTRS = citygml_lod_name
    REGEXP = no
    CASE = no
    REPLACE_TEXT = Geometry
    NO_MATCH = _FME_NO_OP_
    FIND_TEXT = ImplicitRepresentation
    -> GeometryPropertySetter
GeometryPropertySetter
    OVERWRITE_CHOICE = Yes
    SRC_ATTRS = citygml_lod_name
    COUNTER_CHOICE = Attributes
    SETTYPE_PARAM = Traits
    SET -> SolitaryVegetationObject (writer CITYGML_1)
SolitaryVegetationObject (writer CITYGML_1)
    attributes: citygml_relativeToTerrain xml_char(40), citygml_relativeToWater xml_char(40)

FME custom transformer CustomNullAttributeRemover
Checks all the selected attributes and removes them if their contents are 0 or blank. 
This transformer is useful when you need a NULL value written to a database format instead of blank or 0.
The transformer takes one parameter:
Attributes: The attributes to test.
Copyright (c) 2012 Safe Software Inc.
Permission is granted to anyone, free of charge, to use, modify and distribute the object code form of this template for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTRS =   # " " Attributes

INPUT (input)
    -> ParameterFetcher
ParameterFetcher
    ATTR_LIST = _SRC_ATTRS {$(SRC_ATTRS)}
    -> PythonCaller
PythonCaller
    PYTHONSOURCE:
      import fmeobjects
      # Template Function interface:
      def removeNulls(feature):
         attrsin = feature.getAttribute('_SRC_ATTRS')
         attrs = attrsin.split(',')
         for attr in attrs:
             val = feature.getAttribute(attr)
             if not val:
                 feature.removeAttribute(attr)
    PYTHONSYMBOL = removeNulls
    -> AttributeRemover
AttributeRemover
    REMOVE_ATTRS = _SRC_ATTRS
    -> OUTPUT (output)
OUTPUT (output)
