FME workspace Export LandCover.fmw

Parameters:
- SourceDataset_GEODATABASE_FILE_4 =   # Source Esri File Geodatabase
- DestDataset_CITYGML_3 =   # Destination CityGML Document
- citygml_version = 1.0   # CityGML Version
- CityModel_name = 3DCIM CityModel Export   # CityModel Name (gml:name)
- Citymodel_description = 3DCIM CityModel Export   # CityModel description (gml:description)

Readers:
- GEODATABASE_FILE_1: GEODATABASE_FILE from $(SourceDataset_GEODATABASE_FILE_4)

Writers:
- CITYGML_1: CITYGML to $(DestDataset_CITYGML_3)

Note: LandCover
LandCover (reader GEODATABASE_FILE_1)
    attributes: geodb_oid integer, OBJECTID integer, LandCoverFID char(50), name char(100), description char(250), attribution char(250), primaryLandcoverType char(50), primaryLandcoverSubType char(50), secondaryLandcoverType char(50), secondaryLandcoverSubType char(50), density double, verticalExtent double, Shape_Length double, Shape_Area double
    -> GeometryRemover
GeometryRemover
    -> FeatureMerger_5 [input 1]
Note: SpatialVolumeAnnotation
SpatialVolumeAnnotation (reader GEODATABASE_FILE_1)
    attributes: geodb_oid integer, OID integer, SpatialVolumeAnnotationFID char(50), name char(100), description char(250), attribution char(250), referenceFID char(50), value char(250), type coded_domain("AnnotationType:char(50):Comment:Comment:""Process Result"":""Process Result"":Link:Link:Measurement:Measurement"), type_resolved char(254), subtype char(50), beginLifespan date, endLifespan date
    -> AttributeKeeper
SpatialLineAnnotation (reader GEODATABASE_FILE_1)
    attributes: geodb_oid integer, OBJECTID integer, SpatialLineAnnotationFID char(50), name char(100), description char(250), attribution char(250), referenceFID char(50), value char(250), type char(50), subtype char(50), beginLifespan date, endLifespan date, Shape_Length double
    -> AttributeKeeper
AttributeKeeper
    KEEP_ATTRS = attribution,referenceFID
    -> GeometryExtractor
GeometryExtractor
    ATTR = _SpatialVolumeGeometry
    KIND_LONG = FME Binary
    -> GeometryRemover_2
GeometryRemover_2
    -> FeatureMerger_5 [input 2]
FeatureMerger_5
    PROCESS_DUPS = Yes
    MERGE_TYPE = Attributes Only
    LIST_NAME = _Geom
    GEOM_TYPE = Build Polygons
    SUPPLIERS_FIRST = No
    JOIN_KEYS = @Value(LandCoverFID) @Value(referenceFID)
    SUPPLIER_PREFIX_DUMMY = YES
    MERGED -> FeatureMerger [input 1]
    NOT_MERGED -> FeatureMerger [input 1]
Note: AttributeContainer
AttributeContainer (reader GEODATABASE_FILE_1)
    attributes: geodb_oid integer, OBJECTID integer, path char(250), type char(30), value char(250), referenceFID char(50), referenceType char(50)
    -> Aggregator
Aggregator
    GROUP_BY = referenceFID
    MODE = Assemble One Level
    ACCUM_ATTRS_NAME = No
    LIST_NAME = _AttributeContainer
    SEP = ,
    AGGREGATE_TYPE = Homogeneous Collection (If Possible)
    ORDERED = No
    AGGREGATE -> ListElementCounter
ListElementCounter
    LIST_NAME = _AttributeContainer{}
    CNT_ATTR = _element_count
    -> FeatureMerger [input 2]
FeatureMerger
    PROCESS_DUPS = No
    MERGE_TYPE = Attributes Only
    SUPPLIERS_FIRST = No
    JOIN_KEYS = @Value(LandCoverFID) @Value(referenceFID)
    MERGED -> StringReplacer_3
AttributeFilter_3
    ATTR_NAME = citygml_type
    ATTR_VALUES = <BLANK>,<UNFILTERED>,WaterBody,WaterClosureSurface,WaterSurface,WaterGroundSurface,PlantCover,TrafficArea,AuxiliaryTrafficArea
    WaterBody -> AttributeRemover
    WaterClosureSurface -> AttributeSplitter_3
    WaterSurface -> AttributeSplitter_3
    WaterGroundSurface -> AttributeSplitter_3
    PlantCover -> AttributeSplitter_4
    TrafficArea -> AttributeSplitter_5
    AuxiliaryTrafficArea -> AttributeSplitter_5

Bookmark: CityModel
Creator_2
    NUM = 1
    GEOMTYPE = Geometry Object
    CREATED -> AttributeCreator_6
AttributeCreator_6
    ATTR_LIST = gml_name,$(CityModel_name),gml_description,$(Citymodel_description)
    -> CityModel (writer CITYGML_1)
CityModel (writer CITYGML_1)

Bookmark: attribute mapping
Note: replace "/" with "-" for / all attributes used as gml:id / or gml_parent_id
StringReplacer_3
    SRC_ATTRS = LandCoverFID,referenceFID
    REGEXP = no
    CASE = no
    REPLACE_TEXT = -
    NO_MATCH = _FME_NO_OP_
    FIND_TEXT = /
    -> AttributeCopier
AttributeCopier
    ATTR_LIST = gml_id,LandCoverFID
    -> PythonCaller
PythonCaller
    PYTHONSOURCE:
      # Template Class Interface:
      class FeatureProcessor(object):
          def __init__(s):
              pass
          def input(s,f):

              for i in range (0,int(f.getAttribute("_element_count"))):
                  path = f.getAttribute("_AttributeContainer{"+str(i)+"}.path")
                  #logger.logMessageString(path)
                  value = f.getAttribute("_AttributeContainer{"+str(i)+"}.value")
                  #logger.logMessageString(path + value)
                  f.setAttribute(path,value)
              s.pyoutput(f)

          def close(self):
              pass
    PYTHONSYMBOL = FeatureProcessor
    NEW_ATTRIBUTES = citygml_class citygml_function citygml_usage citygml_height_units citygml_trunk_diameter_units citygml_crown_diameter_units gml_parent_id citygml_feature_role citygml_relative_to_terrain citygml_relative_to_water citygml_creationDate citygml_terminationDate citygml_water_level citygml_average_height_units citygml_average_height citygml_surface_material
    -> AttributeRenamer_2
AttributeRenamer_2
    ATTR_LIST = citygml_function,citygml_function_temp,"",citygml_class,citygml_class_temp,""
    -> AttributeSplitter
AttributeSplitter
    LIST_NAME = attributionParts
    ATTR_NAME = attribution
    DELIMITER = /
    TRIM_OPTION = Both
    DROP_EMPTY_PARTS = No
    -> AttributeCreator
AttributeCreator
    ATTR_LIST = citygml_lod_name,@Value(attributionParts{2}),citygml_type,@Value(attributionParts{1})
    -> AttributeRemover_2
AttributeRemover_2
    LIST_ATTRS = attributionParts{} _AttributeContainer{}.type _AttributeContainer{}.referenceType _AttributeContainer{}.referenceFID _AttributeContainer{}.value _AttributeContainer{}.geodb_oid _AttributeContainer{}.path _AttributeContainer{} _AttributeContainer{}.OBJECTID
    -> AttributeRenamer
AttributeRenamer
    ATTR_LIST = name,gml_name,"",description,gml_description,""
    -> Tester
Tester
    TEST_MODE = Automatic
    TEST_DESCRIPTION = ""
    BOOL_OP = OR
    TEST_CLAUSE = TEST @Value(type) = Other
    PASSED -> AttributeRenamer_3
    FAILED -> Tester_2
Tester_2
    TEST_MODE = Automatic
    TEST_DESCRIPTION = ""
    BOOL_OP = OR
    TEST_CLAUSE = TEST @Value(citygml_type) CONTAINS Water
    PASSED -> AttributeValueMapper_3
    FAILED -> AttributeRenamer_3
AttributeValueMapper_3
    DIRECTION = Forward (Source To Destination)
    VAL_ATTR = citygml_class
    LUT = Lake,1060,Wetland,1110
    SRC = primaryLandcoverType
    -> CustomNullAttributeRemover
AttributeRenamer_3
    ATTR_LIST = citygml_function_temp,citygml_function,"",citygml_class_temp,citygml_class,""
    -> CustomNullAttributeRemover
CustomNullAttributeRemover
    SRC_ATTRS = geodb_oid,OBJECTID,LandCoverFID,gml_id,gml_name,gml_description,attribution,primaryLandcoverType,primaryLandcoverSubType,secondaryLandcoverType,secondaryLandcoverSubType,density,verticalExtent,Shape_Length,Shape_Area,referenceFID,path,type,value,referenceType,citygml_usage,citygml_height_units,citygml_trunk_diameter_units,citygml_crown_diameter_units,gml_parent_id,citygml_feature_role,citygml_relative_to_terrain,citygml_relative_to_water,citygml_lod_name,citygml_class_temp,citygml_function_temp
    -> AttributeFilter_3

Bookmark: New Bookmark
AttributeRemover
    REMOVE_ATTRS = attribution
    -> ListExploder
    -> FeatureMerger_3 [input 1]
ListExploder
    INDEX_ATTR = _element_index
    MODE = List Elements and Original Attributes
    LIST_ATTR = _Geom{}
    LIST_FOUND -> GeometryReplacer
GeometryReplacer
    ATTR = _SpatialVolumeGeometry
    KIND_LONG = FME Binary
    -> AttributeSplitter_2
AttributeSplitter_2
    LIST_NAME = attributionParts
    ATTR_NAME = attribution
    DELIMITER = /
    TRIM_OPTION = Both
    DROP_EMPTY_PARTS = No
    -> TestFilter
TestFilter
    TEST_LIST:
      BOOL_OP,OR,COMPOSITE_TEST,<Unused>,TEST_CLAUSE,"TEST @Value(attributionParts{2}) MATCHES_REGEX lod[1-4]Solid",Solid,BOOL_OP,OR,COMPOSITE_TEST,<Unused>,TEST_CLAUSE,"TEST @Value(attributionParts{2}) MATCHES_REGEX lod[0-1]MultiSurface
      TEST @Value(attributionParts{2}) MATCHES_REGEX lod[2-4]Surface",MultiSurface,BOOL_OP,OR,COMPOSITE_TEST,<Unused>,TEST_CLAUSE,"TEST @Value(attributionParts{2}) MATCHES_REGEX lod[0-1]MultiCurve",MultiCurve
    DEFAULT_VALUE = <UNFILTERED>
    Solid -> GeometryCoercer
    MultiSurface -> AttributeCreator_2
    MultiCurve -> AttributeCreator_2
GeometryCoercer
    KIND = fme_composite_surface
    COERCED -> AttributeCreator_2
AttributeCreator_2
    ATTR_LIST = citygml_lod_name,@Value(attributionParts{2})
    -> GeometryPropertySetter_2
GeometryPropertySetter_2
    OVERWRITE_CHOICE = Yes
    SRC_ATTRS = citygml_lod_name
    COUNTER_CHOICE = Attributes
    SETTYPE_PARAM = Traits
    SET -> Tester_3
Tester_3
    TEST_MODE = Automatic
    TEST_DESCRIPTION = ""
    BOOL_OP = OR
    TEST_CLAUSE = TEST @Value(attributionParts{1}) = WaterBody
    PASSED -> Aggregator_2
    FAILED -> AttributeRenamer_4
Aggregator_2
    GROUP_BY = LandCoverFID
    MODE = Assemble One Level
    ACCUM_ATTRS_NAME = No
    SEP = ,
    AGGREGATE_TYPE = Homogeneous Collection (If Possible)
    ORDERED = No
    AGGREGATE -> FeatureMerger_3 [input 2]
FeatureMerger_3
    PROCESS_DUPS = No
    MERGE_TYPE = Attributes and Geometry
    SUPPLIERS_FIRST = No
    JOIN_KEYS = @Value(LandCoverFID) @Value(LandCoverFID)
    SUPPLIER_PREFIX_DUMMY = YES
    MERGED -> WaterBody (writer CITYGML_1)
    NOT_MERGED -> WaterBody (writer CITYGML_1)
Note: WaterBody
WaterBody (writer CITYGML_1)
    attributes: citygml_relative_to_terrain xml_char(33), citygml_relative_to_water xml_char(38)
AttributeRenamer_4
    ATTR_LIST = gml_id,gml_parent_id,""
    -> AttributeCreator_4
AttributeCreator_4
    ATTR_LIST = citygml_feature_role,boundedBy
    -> AttributeCreator_5
AttributeCreator_5
    ATTR_LIST = citygml_type,@Value(attributionParts{1})
    -> WaterSurface (writer CITYGML_1)
AttributeSplitter_3
    LIST_NAME = attributionParts
    ATTR_NAME = attribution
    DELIMITER = /
    TRIM_OPTION = Both
    DROP_EMPTY_PARTS = No
    -> AttributeCreator_3
AttributeCreator_3
    ATTR_LIST = citygml_lod_name,@Value(attributionParts{2})
    -> GeometryPropertySetter_3
GeometryPropertySetter_3
    OVERWRITE_CHOICE = Yes
    SRC_ATTRS = citygml_lod_name
    COUNTER_CHOICE = Attributes
    SETTYPE_PARAM = Traits
    SET -> WaterSurface (writer CITYGML_1)
Note: WaterSurface\WaterClosureSurface\WaterGroundSurface
WaterSurface (writer CITYGML_1)
    attributes: citygml_relative_to_terrain xml_char(33), citygml_relative_to_water xml_char(38)

Bookmark: PlantCover
AttributeSplitter_4
    LIST_NAME = attributionParts
    ATTR_NAME = attribution
    DELIMITER = /
    TRIM_OPTION = Both
    DROP_EMPTY_PARTS = No
    -> TestFilter_2
TestFilter_2
    TEST_LIST = BOOL_OP,OR,COMPOSITE_TEST,<Unused>,TEST_CLAUSE,"TEST @Value(attributionParts{2}) MATCHES_REGEX lod[1-4]MultiSolid",MultiSolid,BOOL_OP,OR,COMPOSITE_TEST,<Unused>,TEST_CLAUSE,"TEST @Value(attributionParts{2}) MATCHES_REGEX lod[1-4]MultiSurface",MultiSurface
    DEFAULT_VALUE = <UNFILTERED>
    MultiSolid -> GeometryCoercer_2
    MultiSurface -> AttributeCreator_7
GeometryCoercer_2
    KIND = fme_brep_solid
    COERCED -> AttributeCreator_7
AttributeCreator_7
    ATTR_LIST = citygml_lod_name,@Value(attributionParts{2})
    -> GeometryPropertySetter_4
GeometryPropertySetter_4
    OVERWRITE_CHOICE = Yes
    SRC_ATTRS = citygml_lod_name
    COUNTER_CHOICE = Attributes
    SETTYPE_PARAM = Traits
    SET -> PlantCover00 (writer CITYGML_1)
PlantCover00 (writer CITYGML_1)
    attributes: citygml_relative_to_terrain xml_char(33), citygml_relative_to_water xml_char(38)

Bookmark: TrafficArea
AttributeSplitter_5
    LIST_NAME = attributionParts
    ATTR_NAME = attribution
    DELIMITER = /
    TRIM_OPTION = Both
    DROP_EMPTY_PARTS = No
    -> AttributeCreator_8
AttributeCreator_8
    ATTR_LIST = citygml_lod_name,@Value(attributionParts{2})
    -> GeometryPropertySetter_5
GeometryPropertySetter_5
    OVERWRITE_CHOICE = Yes
    SRC_ATTRS = citygml_lod_name
    COUNTER_CHOICE = Attributes
    SETTYPE_PARAM = Traits
    SET -> Transportation (writer CITYGML_1)
Transportation (writer CITYGML_1)
    attributes: citygml_relative_to_terrain xml_char(33), citygml_relative_to_water xml_char(38)

FME custom transformer CustomNullAttributeRemover
Checks all the selected attributes and removes them if their contents are 0 or blank. 
This transformer is useful when you need a NULL value written to a database format instead of blank or 0.
The transformer takes one parameter:
Attributes: The attributes to test.
Copyright (c) 2012 Safe Software Inc.
Permission is granted to anyone, free of charge, to use, modify and distribute the object code form of this template for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTRS =   # " " Attributes

INPUT (input)
    -> ParameterFetcher
ParameterFetcher
    ATTR_LIST = _SRC_ATTRS {$(SRC_ATTRS)}
    -> PythonCaller
PythonCaller
    PYTHONSOURCE:
      import fmeobjects
      # Template Function interface:
      def removeNulls(feature):
         attrsin = feature.getAttribute('_SRC_ATTRS')
         attrs = attrsin.split(',')
         for attr in attrs:
             val = feature.getAttribute(attr)
             if not val:
                 feature.removeAttribute(attr)
    PYTHONSYMBOL = removeNulls
    -> AttributeRemover
AttributeRemover
    REMOVE_ATTRS = _SRC_ATTRS
    -> OUTPUT (output)
OUTPUT (output)
