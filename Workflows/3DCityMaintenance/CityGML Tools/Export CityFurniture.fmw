FME workspace Export CityFurniture.fmw

Parameters:
- SourceDataset_GEODATABASE_FILE =   # Source Esri File Geodatabase
- DestDataset_CITYGML_3 =   # Destination CityGML Document
- citygml_version = 1.0   # CityGML Version
- CityModel_name = 3DCIM CityModel Export   # CityModel Name (gml:name)
- Citymodel_description = 3DCIM CityModel Export   # CityModel description (gml:description)

Readers:
- GEODATABASE_FILE_1: GEODATABASE_FILE from $(SourceDataset_GEODATABASE_FILE)

Writers:
- CITYGML_1: CITYGML to $(DestDataset_CITYGML_3)

Bookmark: StreetFurniture - CityFurniture
StreetFurniture (reader GEODATABASE_FILE_1)
    attributes: geodb_oid integer, OBJECTID integer, StreetFurnitureFID char(50), name char(100), description char(250), attribution char(250), type coded_domain("StreetFurnitureType:char(30):Bench:Bench:""Bus Shelter"":""Bus Shelter"":Planter:Planter:""Trash Can"":""Trash Can"":""Bike Rack"":""Bike Rack"":Bollard:Bollard:""Tree Grate"":""Tree Grate"":""Tree Guard"":""Tree Guard"":""Post Box"":""Post Box"":Kiosk:Kiosk:Barricade:Barricade:""Information Sign"":""Information Sign"":Table:Table:Monument:Monument:Sculpture:Sculpture:Banner:Banner:""Newspaper Dispenser"":""Newspaper Dispenser"":""Fire Hydrant"":""Fire Hydrant"":Other:Other:Unknown:Unknown"), type_resolved char(254), subtype char(50), rotation double, beginLifespan date, endLifespan date
    -> FeatureMerger [input 1]
AttributeContainer (reader GEODATABASE_FILE_1)
    attributes: geodb_oid integer, OBJECTID integer, path char(250), type char(30), value char(250), referenceFID char(50), referenceType char(50)
    -> Aggregator
Aggregator
    GROUP_BY = referenceFID
    MODE = Assemble One Level
    ACCUM_ATTRS_NAME = No
    LIST_NAME = _AttributeContainer
    SEP = ,
    AGGREGATE_TYPE = Homogeneous Collection (If Possible)
    ORDERED = No
    AGGREGATE -> ListElementCounter
ListElementCounter
    LIST_NAME = _AttributeContainer{}
    CNT_ATTR = _element_count
    -> FeatureMerger [input 2]
FeatureMerger
    PROCESS_DUPS = No
    MERGE_TYPE = Attributes Only
    SUPPLIERS_FIRST = No
    JOIN_KEYS = @Value(StreetFurnitureFID) @Value(referenceFID)
    MERGED -> GeometryRemover
    NOT_MERGED -> GeometryRemover
GeometryRemover
    -> StringReplacer_3
Note: replace "/" with "-" for / all attributes used as gml:id / or gml_parent_id
StringReplacer_3
    SRC_ATTRS = referenceFID
    REGEXP = no
    CASE = no
    REPLACE_TEXT = -
    NO_MATCH = _FME_NO_OP_
    FIND_TEXT = /
    -> PythonCaller
PythonCaller
    PYTHONSOURCE:
      # Template Class Interface:
      class FeatureProcessor(object):
          def __init__(s):
              pass
          def input(s,f):

              for i in range (0,int(f.getAttribute("_element_count"))):
                  path = f.getAttribute("_AttributeContainer{"+str(i)+"}.path")
                  #logger.logMessageString(path)
                  value = f.getAttribute("_AttributeContainer{"+str(i)+"}.value")
                  #logger.logMessageString(path + value)
                  f.setAttribute(path,value)
              s.pyoutput(f)

          def close(self):
              pass
    PYTHONSYMBOL = FeatureProcessor
    NEW_ATTRIBUTES = gml_id citygml_class citygml_function citygml_usage citygml_height_units citygml_trunk_diameter_units citygml_crown_diameter_units gml_parent_id citygml_feature_role citygml_relativeToTerrain citygml_relativeToWater
    -> AttributeRemover_3
AttributeRemover_3
    LIST_ATTRS = _AttributeContainer{}.type _AttributeContainer{}.referenceType _AttributeContainer{}.referenceFID _AttributeContainer{}.value _AttributeContainer{}.geodb_oid _AttributeContainer{}.path _AttributeContainer{} _AttributeContainer{}.OBJECTID
    -> AttributeRenamer_2
AttributeRenamer_2
    ATTR_LIST = citygml_function,citygml_function_temp,""
    -> FeatureMerger_2 [input 1]
SpatialVolumeAnnotation (reader GEODATABASE_FILE_1)
    attributes: geodb_oid integer, OID integer, SpatialVolumeAnnotationFID char(50), name char(100), description char(250), attribution char(250), referenceFID char(50), value char(250), type coded_domain("AnnotationType:char(50):Comment:Comment:""Process Result"":""Process Result"":Link:Link:Measurement:Measurement"), type_resolved char(254), subtype char(50), beginLifespan date, endLifespan date
    -> FeatureMerger_2 [input 2]
FeatureMerger_2
    PROCESS_DUPS = No
    MERGE_TYPE = Attributes and Geometry
    SUPPLIERS_FIRST = No
    JOIN_KEYS = @Value(StreetFurnitureFID) @Value(referenceFID)
    MERGED -> CustomNullAttributeRemover
    NOT_MERGED -> CustomNullAttributeRemover
CustomNullAttributeRemover
    SRC_ATTRS = geodb_oid,OBJECTID,StreetFurnitureFID,name,description,attribution,type,type_resolved,subtype,rotation,beginLifespan,endLifespan,path,value,referenceFID,referenceType,_element_count,gml_id,citygml_class,citygml_function_temp,citygml_usage,citygml_height_units,citygml_trunk_diameter_units,citygml_crown_diameter_units,gml_parent_id,citygml_feature_role,OID,SpatialVolumeAnnotationFID
    -> AttributeSplitter
AttributeSplitter
    LIST_NAME = attributionParts
    ATTR_NAME = attribution
    DELIMITER = /
    TRIM_OPTION = Both
    DROP_EMPTY_PARTS = No
    -> AttributeCreator
AttributeCreator
    ATTR_LIST = citygml_lod_name,@Value(attributionParts{2})
    -> StringReplacer
StringReplacer
    SRC_ATTRS = citygml_lod_name
    REGEXP = no
    CASE = no
    REPLACE_TEXT = Geometry
    NO_MATCH = _FME_NO_OP_
    FIND_TEXT = ImplicitRepresentation
    -> GeometryPropertySetter
GeometryPropertySetter
    OVERWRITE_CHOICE = Yes
    SRC_ATTRS = citygml_lod_name
    COUNTER_CHOICE = Attributes
    SETTYPE_PARAM = Traits
    SET -> AttributeRenamer
AttributeRenamer
    ATTR_LIST = beginLifespan,citygml_creationDate,"",endLifespan,citygml_terminationDate,"",name,gml_name,"",description,gml_description,""
    -> TestFilter
TestFilter
    TEST_LIST = BOOL_OP,OR,COMPOSITE_TEST,<Unused>,TEST_CLAUSE,"TEST citygml_creationDate NOT_ATTRIBUTE_IS_EMPTY <Unused>",creationDate,BOOL_OP,OR,COMPOSITE_TEST,<Unused>,TEST_CLAUSE,"TEST citygml_terminationDate NOT_ATTRIBUTE_IS_EMPTY <Unused>",terminationDate
    DEFAULT_VALUE = <UNFILTERED>
    creationDate -> DateFormatter
    terminationDate -> DateFormatter_2
    <UNFILTERED> -> Tester
DateFormatter
    DATE_ATTR = citygml_creationDate
    FMT = XML Date (%Y-%m-%d)
    -> Tester
DateFormatter_2
    DATE_ATTR = citygml_terminationDate
    FMT = XML Date (%Y-%m-%d)
    -> Tester
Tester
    TEST_MODE = Automatic
    TEST_DESCRIPTION = ""
    BOOL_OP = OR
    TEST_CLAUSE = TEST @Value(type) = Other
    FAILED -> AttributeValueMapper
    PASSED -> AttributeRenamer_3
AttributeRenamer_3
    ATTR_LIST = citygml_function_temp,citygml_function,""
    -> AttributeRemover
AttributeValueMapper
    DIRECTION = Forward (Source To Destination)
    VAL_ATTR = citygml_function
    LUT = Bus Shelter,1110,Fire Hydrant,1330,Information Sign,1090,Post Box,1020,Trash Can,1200,Bench,1530,Monument,1450
    SRC = type
    -> AttributeRemover
AttributeRemover
    LIST_ATTRS = attributionParts{} _AttributeContainer{}.type _AttributeContainer{}.referenceType _AttributeContainer{}.referenceFID _AttributeContainer{}.value _AttributeContainer{}.geodb_oid _AttributeContainer{}.path _AttributeContainer{} _AttributeContainer{}.OBJECTID
    REMOVE_ATTRS = citygml_species_temp
    -> Aggregator_2
Aggregator_2
    GROUP_BY = gml_id
    MODE = Assemble One Level
    ACCUM_ATTRS_NAME = Yes
    SEP = ,
    AGGREGATE_TYPE = Homogeneous Collection (If Possible)
    ORDERED = No
    AGGREGATE -> CityFurniture (writer CITYGML_1)
CityFurniture (writer CITYGML_1)
    attributes: citygml_relativeToTerrain xml_char(30), citygml_relativeToWater xml_char(40)

Bookmark: CityModel
Creator_2
    NUM = 1
    GEOMTYPE = Geometry Object
    CREATED -> AttributeCreator_6
AttributeCreator_6
    ATTR_LIST = gml_name,$(CityModel_name),gml_description,$(Citymodel_description)
    -> CityModel (writer CITYGML_1)
CityModel (writer CITYGML_1)

FME custom transformer CustomNullAttributeRemover
Checks all the selected attributes and removes them if their contents are 0 or blank. 
This transformer is useful when you need a NULL value written to a database format instead of blank or 0.
The transformer takes one parameter:
Attributes: The attributes to test.
Copyright (c) 2012 Safe Software Inc.
Permission is granted to anyone, free of charge, to use, modify and distribute the object code form of this template for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- SRC_ATTRS =   # " " Attributes

INPUT (input)
    -> ParameterFetcher
ParameterFetcher
    ATTR_LIST = _SRC_ATTRS {$(SRC_ATTRS)}
    -> PythonCaller
PythonCaller
    PYTHONSOURCE:
      import fmeobjects
      # Template Function interface:
      def removeNulls(feature):
         attrsin = feature.getAttribute('_SRC_ATTRS')
         attrs = attrsin.split(',')
         for attr in attrs:
             val = feature.getAttribute(attr)
             if not val:
                 feature.removeAttribute(attr)
    PYTHONSYMBOL = removeNulls
    -> AttributeRemover
AttributeRemover
    REMOVE_ATTRS = _SRC_ATTRS
    -> OUTPUT (output)
OUTPUT (output)
