FME workspace Import CityFurniture.fmw

Parameters:
- SourceDataset_CITYGML =   # Source CityGML File(s)
- CITYGML_IN_SRS_AXIS_ORDER_CITYGML =   # GML SRS Axis Order (optional)
- CITYGML_IN_SKIP_SCHEMA_LOCATION_IN_DATASET_CITYGML = Yes   # Ignore xsi:schemaLocation in Dataset (optional)
- DestDataset_GEODATABASE_FILE =   # Destination Esri File Geodatabase
- GEODATABASE_FILE_OUT_TEMPLATEFILE_GEODATABASE_FILE =   # XML Workspace Document (for initial creation of Geodatabase schema)
- GEODATABASE_FILE_OUT_OVERWRITE_GEODB_GEODATABASE_FILE = No   # Overwrite Existing Geodatabase

Readers:
- CITYGML_1: CITYGML from $(SourceDataset_CITYGML)

Writers:
- GEODATABASE_FILE_1: GEODATABASE_FILE to $(DestDataset_GEODATABASE_FILE)

Bookmark: CityFurniture - StreetFurniture
CityFurniture (reader CITYGML_1)
    attributes: citygml_target_uri xml_buffer, citygml_feature_role_attr_name xml_buffer, citygml_feature_role_attr_val xml_buffer, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class_codeSpace xml_buffer, citygml_level_of_detail{} xml_buffer
    -> AttributeValueMapper_3
AttributeValueMapper_3
    DIRECTION = Forward (Source To Destination)
    VAL_ATTR = type
    DEFAULT_VALUE = Other
    LUT = 1000,Other,1010,Other,1020,Post Box,1030,Other,1040,Other,1050,Other,1060,Other,1070,Information Sign,1080,Other,1090,Information Sign,1100,Information Sign,1110,Bus Shelter,1120,Other,1130,Other,1140,Other,1150,Other,1160,Other,1170,Other,1180,Banner,1190,Other,1200,Trash Can,1210,Other,1220,Other,1230,Other,1240,Other,1250,Other,1260,Other,1270,Other,1280,Other,1290,Other,1300,Other,1310,Other,1320,Information Sign,1330,Fire Hydrant,1340,Fire Hydrant,1350,Fire Hydrant,1360,Other,1370,Other,1380,Other,1390,Other,1400,Other,1410,Other,1420,Other,1430,Other,1440,Other,1450,Monument,1460,Other,1470,Other,1480,Other,1490,Other,1500,Other,1510,Other,1520,Other,1530,Bench,1540,Other
    SRC = citygml_function
    -> AttributeCreator_2
Note: Create FID
AttributeCreator_2
    ATTR_LIST = FID,@Value(fme_feature_type)/@Value(type)/@Count(@Value(fme_feature_type))/1
    -> AttributeRenamer_2
Note: general attribute mapping
AttributeRenamer_2
    ATTR_LIST = gml_name,name,"",gml_description,description,"",citygml_creationDate,beginLifespan,"",citygml_terminationDate,endLifespan,""
    -> GeometryPropertyExtractor
AttributeKeeper
    KEEP_ATTRS = gml_id,gml_parent_id,citygml_feature_role,description,name,beginLifespan,endLifespan,citygml_class,citygml_function,citygml_usage,fme_feature_type,type,FID,attribution
    -> DateFormatter
Note: format beginLifespan, / endLifespan
DateFormatter
    DATE_ATTR = beginLifespan,endLifespan
    FMT = FME Date (%Y%m%d)
    SRCFMT = %Y-%m-%d
    -> AttributeCopier_2
AttributeCopier_2
    ATTR_LIST = subtype,citygml_function
    -> AttributeRenamer_3
    -> AttributeRenamer_4
AttributeRenamer_3
    ATTR_LIST = FID,StreetFurnitureFID,""
    -> BoundsExtractor_6
BoundsExtractor_6
    ZMIN = _zmin
    -> GeometryFilter_2
GeometryFilter_2
    BREAK_AGG = No
    SURFACE -> CenterPointReplacer_5
    SOLID -> CenterPointReplacer_5
    LINE -> CoordinateExtractor
CoordinateExtractor
    Y_ATTR = _ymin
    X_ATTR = _xmin
    Z_DEFAULT = -9999
    Z_ATTR = _z
    IND = 0
    -> 3DPointReplacer_3
CenterPointReplacer_5
    CENTERPOINT -> BoundsExtractor_7
BoundsExtractor_7
    YMIN = _ymin
    XMIN = _xmin
    -> 3DPointReplacer_3
3DPointReplacer_3
    XVALATTR = @Value(_xmin)
    ZVALATTR = @Value(_zmin)
    YVALATTR = @Value(_ymin)
    POINT -> StreetFurniture (writer GEODATABASE_FILE_1)
StreetFurniture (writer GEODATABASE_FILE_1)
    attributes: StreetFurnitureFID char(50), name char(100), description char(250), attribution char(250), type char(30), subtype char(50), rotation double, beginLifespan date, endLifespan date
AttributeRenamer_4
    ATTR_LIST = FID,referenceFID,""
    -> StringConcatenator
StringConcatenator
    PARM_LINE = SpatialVolumeAnnotation/@Value(type)/@Count(SpatialVolumeAnnotation)/1
    VAL_ATTR = SpatialVolumeAnnotationFID
    -> GeometryFilter
GeometryFilter
    BREAK_AGG = No
    SOLID -> SpatialVolumeAnnotation (writer GEODATABASE_FILE_1)
    SURFACE -> SpatialVolumeAnnotation (writer GEODATABASE_FILE_1)
    LINE -> AttributeRenamer
    ARC -> AttributeRenamer
AttributeRenamer
    ATTR_LIST = SpatialVolumeAnnotationFID,SpatialLineAnnotationFID,""
    -> SpatialLineAnnotation (writer GEODATABASE_FILE_1)
SpatialLineAnnotation (writer GEODATABASE_FILE_1)
    attributes: geodb_oid integer, OBJECTID integer, SpatialLineAnnotationFID char(50), name char(100), description char(250), attribution char(250), referenceFID char(50), value char(250), type char(50), subtype char(50), beginLifespan date, endLifespan date, Shape_Length double
SpatialVolumeAnnotation (writer GEODATABASE_FILE_1)
    attributes: SpatialVolumeAnnotationFID char(50), name char(100), description char(250), attribution char(250), referenceFID char(50), value char(250), type char(50), subtype char(50), beginLifespan date, endLifespan date

Bookmark: attribution
  store CityGML filename + feature type + geometry_name
GeometryPropertyExtractor
    TRAIT_ATTR_LIST = citygml_lod_name
    GQUERY:
      for $geom in //geometry
      where $geom/count(parent::geometry) = 0
      return number($geom/@fme_id)
    PREFIX_EXTRACTED_TRAITS = No
    EXTRACTTYPE_PARAM = Traits
    EXTRACTED -> StringConcatenator_2
    UNTOUCHED -> StringConcatenator_2
StringConcatenator_2
    PARM_LINE = @Value(fme_basename)/@Value(fme_feature_type)/@Value(citygml_lod_name)
    VAL_ATTR = attribution
    -> PythonCaller

Bookmark: AttributeContainer handling (all attributes not explicitly mapped)
PythonCaller
    PYTHONSOURCE:
      from fmeobjects import FMEFeature
      from re import match

      # Template Class Interface:
      class FeatureProcessor(object):

          def __init__(s):
              #,"citygml_measured_height"
              s.DoNotMapList =[
                  "^fme_.*",
                  "name","xml_type","attribution","citygml_feature_role","citygml_level_of_detail{0}","_FeatureClass","FID",
                  "description","beginLifespan","endLifespan","type","gml_parent_id",
              "citygml_usage","citygml_roof_type","citygml_storeys_above_ground",
              "citygml_storeys_below_ground"]


          def input(s,f):
              #get FeatureType
              fType = f.getAttribute("fme_feature_type")

              if fType == "CityModel":
                  return
              #get AllAttributes
              allAttr = f.getAllAttributeNames()

              ### Nur Attribute, die nicht auf die DoNotMapListe matchen
              for a in filter(lambda x: not any(match(regex,x) for regex in s.DoNotMapList), allAttr):
                  aValue = f.getAttribute(a)
                  #if aValue is None or aValue == "" or aValue is u"":
                  if not aValue:
                      next
                  #New AttributeContainer Feature
                  nF = FMEFeature()
                  #containerFeature.setFeatureType("AttributeContainer")
                  nF.setAttribute("isAttributeContainer","True")
                  #print a
                  nF.setAttribute("path",a)
                  nF.setAttribute("type",0)
                  nF.setAttribute("value",aValue)
                  nF.setAttribute("referenceFID",f.getAttribute("FID"))
                  nF.setAttribute("referenceType",fType)
                  s.pyoutput(nF)

              s.pyoutput(f)

          def close(s):
              pass
    PYTHONSYMBOL = FeatureProcessor
    NEW_ATTRIBUTES = fme_feature_type isAttributeContainer referenceFID referenceType path value type
    -> Tester_2
Tester_2
    TEST_MODE = Automatic
    TEST_DESCRIPTION = ""
    BOOL_OP = OR
    TEST_CLAUSE = TEST @Value(isAttributeContainer) = True
    FAILED -> AttributeKeeper
    PASSED -> AttributeContainer (writer GEODATABASE_FILE_1)
AttributeContainer (writer GEODATABASE_FILE_1)
    attributes: path char(250), type char(30), value char(250), referenceFID char(50), referenceType char(50)
