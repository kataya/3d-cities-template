FME workspace Import LandUse.fmw

Parameters:
- SourceDataset_CITYGML_3 =   # Source CityGML File(s)
- CITYGML_IN_SRS_AXIS_ORDER_CITYGML =   # GML SRS Axis Order
- CITYGML_IN_SKIP_SCHEMA_LOCATION_IN_DATASET_CITYGML = Yes   # Ignore xsi:schemaLocation in Dataset
- DestDataset_GEODATABASE_FILE =   # Destination Esri File Geodatabase
- GEODATABASE_FILE_OUT_TEMPLATEFILE_GEODATABASE_FILE =   # XML Workspace Document (for initial creation of Geodatabase schema)
- GEODATABASE_FILE_OUT_OVERWRITE_GEODB_GEODATABASE_FILE = No   # Overwrite Existing Geodatabase

Readers:
- CITYGML_1: CITYGML from $(SourceDataset_CITYGML_3)

Writers:
- GEODATABASE_FILE_1: GEODATABASE_FILE to $(DestDataset_GEODATABASE_FILE)

Bookmark: LandUse - ZoningDistrict
LandUse (reader CITYGML_1)
    attributes: citygml_target_uri xml_buffer, citygml_feature_role_attr_name xml_buffer, citygml_feature_role_attr_val xml_buffer, externalReference{}.externalObject.name xml_xml, externalReference{}.externalObject.uri xml_xml, externalReference{}.informationSystem xml_xml, citygml_generalizes_to{}.xlink_href xml_buffer, citygml_appearance{}.xlink_href xml_buffer, citygml_level_of_detail{} xml_buffer
    -> AttributeValueMapper_5
AttributeValueMapper_5
    DIRECTION = Forward (Source To Destination)
    VAL_ATTR = type
    DEFAULT_VALUE = Other
    LUT = 1010,Residential Single,1020,Industrial,1030,Other,1040,Other,1050,Other,1060,Utility,1070,Industrial,1110,Open Space,1120,Other,1130,Public,1140,Industrial,2010,Transport,2020,Transport,2030,Transport,2040,Transport,2050,Transport,2060,Transport,3010,Open Space,3020,Agricultural,3030,Open Space,3040,Open Space,3050,Open Space,3060,Open Space,3070,Open Space,3080,Open Space,4010,Other,4020,Other,4030,Transport,4040,Other
    SRC = citygml_function
    -> AttributeCreator_2
AttributeCreator_2
    ATTR_LIST = FID,@Value(fme_feature_type)/@Value(type)/@Count(@Value(fme_feature_type))/1
    -> AttributeRenamer_2
Note: general attribute mapping
AttributeRenamer_2
    ATTR_LIST = gml_name,name,"",gml_description,description,"",citygml_creationDate,beginLifespan,"",citygml_terminationDate,endLifespan,""
    -> GeometryPropertyExtractor
Note: format beginLifespan, / endLifespan
DateFormatter
    DATE_ATTR = beginLifespan,endLifespan
    FMT = FME Date (%Y%m%d)
    SRCFMT = %Y-%m-%d
    -> AttributeCopier_2
AttributeCopier_2
    ATTR_LIST = subtype,citygml_function
    -> AttributeRenamer_4
    -> AttributeRenamer_3
AttributeRenamer_3
    ATTR_LIST = type,usageType,"",FID,referenceFID,""
    -> GeometryRemover
GeometryRemover
    -> Usage (writer GEODATABASE_FILE_1)
Usage (writer GEODATABASE_FILE_1)
    attributes: referenceFID char(50), usageType char(50), usagePortion double, verticalExtentMin double, verticalExtentMax double, verticalExtentUnit char(50)
AttributeRenamer_4
    ATTR_LIST = FID,ZoningDistrictFID,"",type,zoningPlanType,""
    -> Deaggregator
Deaggregator
    LIST_ATTR_MODE_LOOKUP = LEAN
    MODE = Flatten All Levels
    SPLIT_COMPOSITES = Yes
    EXPLODE_INSTANCES = No
    GEOM_NAME_FIELD = _geometry_name
    DEAGGREGATED -> GeometryCoercer
GeometryCoercer
    CHECKZ = No
    KIND = fme_polygon
    COERCED -> Aggregator
Aggregator
    GROUP_BY = ZoningDistrictFID
    MODE = Assemble One Level
    ACCUM_ATTRS_NAME = Yes
    SEP = ,
    AGGREGATE_TYPE = Homogeneous Collection (If Possible)
    ORDERED = No
    AGGREGATE -> ZoningDistrict (writer GEODATABASE_FILE_1)
ZoningDistrict (writer GEODATABASE_FILE_1)
    attributes: ZoningDistrictFID char(50), name char(100), description char(250), attribution char(250), transect char(10), zoningPlanType char(30), verticalExtentMin double, verticalExtentMax double, verticalExtentUnit char(30), overlay smallint, beginLifespan date, endLifespan date

Bookmark: attribution
  store CityGML filename + feature type + geometry_name
GeometryPropertyExtractor
    TRAIT_ATTR_LIST = citygml_lod_name
    GQUERY:
      for $geom in //geometry
      where $geom/count(parent::geometry) = 0
      return number($geom/@fme_id)
    PREFIX_EXTRACTED_TRAITS = No
    EXTRACTTYPE_PARAM = Traits
    EXTRACTED -> StringConcatenator_2
    UNTOUCHED -> StringConcatenator_2
StringConcatenator_2
    PARM_LINE = @Value(fme_basename)/@Value(fme_feature_type)/@Value(citygml_lod_name)
    VAL_ATTR = attribution
    -> PythonCaller

Bookmark: AttributeContainer handling (all attributes not explicitly mapped)
PythonCaller
    PYTHONSOURCE:
      from fmeobjects import FMEFeature
      from re import match

      # Template Class Interface:
      class FeatureProcessor(object):

          def __init__(s):
              #,"citygml_measured_height"
              s.DoNotMapList =[
                  "^fme_.*",
                  "name","xml_type","attribution","citygml_feature_role","citygml_level_of_detail{0}","_FeatureClass","FID",
                  "description","beginLifespan","endLifespan","type","gml_parent_id",
              "citygml_usage","citygml_roof_type","citygml_storeys_above_ground",
              "citygml_storeys_below_ground","citygml_function"]


          def input(s,f):
              #get FeatureType
              fType = f.getAttribute("fme_feature_type")

              if fType == "CityModel":
                  return
              #get AllAttributes
              allAttr = f.getAllAttributeNames()

              ### Nur Attribute, die nicht auf die DoNotMapListe matchen
              for a in filter(lambda x: not any(match(regex,x) for regex in s.DoNotMapList), allAttr):
                  aValue = f.getAttribute(a)
                  #if aValue is None or aValue == "" or aValue is u"":
                  if not aValue:
                      next
                  #New AttributeContainer Feature
                  nF = FMEFeature()
                  #containerFeature.setFeatureType("AttributeContainer")
                  nF.setAttribute("isAttributeContainer","True")
                  #print a
                  nF.setAttribute("path",a)
                  nF.setAttribute("type",0)
                  nF.setAttribute("value",aValue)
                  nF.setAttribute("referenceFID",f.getAttribute("FID"))
                  nF.setAttribute("referenceType",fType)
                  s.pyoutput(nF)

              s.pyoutput(f)

          def close(s):
              pass
    PYTHONSYMBOL = FeatureProcessor
    NEW_ATTRIBUTES = fme_feature_type isAttributeContainer referenceFID referenceType path value type
    -> Tester_2
Tester_2
    TEST_MODE = Automatic
    TEST_DESCRIPTION = ""
    BOOL_OP = OR
    TEST_CLAUSE = TEST @Value(isAttributeContainer) = True
    FAILED -> AttributeKeeper
    PASSED -> AttributeContainer (writer GEODATABASE_FILE_1)
AttributeContainer (writer GEODATABASE_FILE_1)
    attributes: path char(250), type char(30), value char(250), referenceFID char(50), referenceType char(50)
AttributeKeeper
    KEEP_LIST = citygml_address{}
    KEEP_ATTRS = gml_id,gml_parent_id,citygml_feature_role,description,name,beginLifespan,endLifespan,citygml_address,citygml_height_units,citygml_measured_height,citygml_usage,citygml_function,citygml_year_of_demolition,citygml_height,citygml_year_of_construction,citygml_class,fme_feature_type,type,FID,attribution
    -> DateFormatter
